FME workspace Pobierania_zdjec_satelitarnych_USGS.fmw
Title: CompleteWorkspace

Parameters:
- individual_id = 430270991   # Individual Bird ID
- DestDataset_GEOJSON = C:\Users\eliza\Desktop\eagle.json   # Destination GeoJSON File
- api_key_m2m = eyJjaWQiOjI0NTgwMTY3LCJzIjoiMTYxNDYyNjQ1MiIsInIiOjI3MywicCI6WyJkb3dubG9hZCIsIm9yZGVyIl19   # api_key
- cloudCover_max = 15
- Start_date = 1984-03-01
- End_date = 2021-02-23
- entityId = 232835
- datasetName_Sentinel2 = sentinel_2a
- latitude_ll = 48.8
- longitude_ll = 18.4
- latitude_ur = 51.18
- longitude_ur = 24.7
- startDate_sentinel = 2016-01-01
- endDate_sentinel = 2021-03-15
- ZIP_Path_Sentinel = C:\Users\eliza\Desktop\Sentinel_2.zip
- datasetName_Landsat8 = landsat_8_c1
- endDate_Landsat8 = 2021-12-31
- startDate_Landsat8 = 2019-01-01
- ZIP_Path_Landsat8 = C:\Users\eliza\Desktop\Landsat_8.tar.gz
- SourceDataset_XLSXR = C:\Users\eliza\Desktop\Daty_Sentinel2.xlsx   # Source Microsoft Excel File(s)
- SourceDataset_XLSXR_3 = C:\Users\eliza\Desktop\Daty_Sentinel2.xlsx   # Source Microsoft Excel File(s)
- DestDataset_XLSXW = C:\Users\eliza\Desktop\Daty_Sentinel2.xlsx   # Destination Microsoft Excel File
- TXT_Path_Sentinel = C:\Users\eliza\Desktop\Dane\Daty_Sentinel.txt
- TXT_Path_Landsat_8 = C:\Users\eliza\Desktop\Dane\Daty_Landsat_8.txt
- datasetName_Landsat7 = landsat_etm_c1
- startDate_Landsat7 = 2002-01-01
- endDate_Landsat7 = 2002-12-31
- datasetName_Landsat5 = gls_all
- startDate_Landsat5 = 1999-01-01
- endDate_Landsat5 = 2013-01-06
- TXT_Landsat_7 = C:\Users\eliza\Desktop\Dane\Daty_Landsat_7.txt
- TXT_Landsat_5 = C:\Users\eliza\Desktop\Dane\Daty_Landsat_5.txt
- ZIP_Path_Landsat5 = C:\Users\eliza\Desktop\Landsat_5.tar.gz
- SourceDataset_PATH = C:\Users\eliza\Desktop\Landsat_5   # Source Folder and File Pathnames Folder
- SourceDataset_PATH_9 = C:\Users\eliza\Desktop\Dane_obszary_badawcze   # Source Folder and File Pathnames Folder
- SourceDataset_PATH_13 = C:\Users\eliza\Desktop\Dane_obszary_badawcze   # Source Folder and File Pathnames Folder
- SourceDataset_OGCKML = C:\Users\eliza\Desktop\Dane_obszary_badawcze\ry1.kmz   # Source Google KML File or URL
- DestDataset_SHAPEFILE = C:\Users\eliza\Desktop\Dane_obszary_badawcze\esri   # Destination Esri Shapefile Folder
- SourceDataset_OGCKML_3 = C:\Users\eliza\Desktop\Dane_obszary_badawcze\ry1.kmz   # Source Google KML File or URL
- DestDataset_SHAPEFILE_3 = C:\Users\eliza\Desktop\Dane_obszary_badawcze\esri   # Destination Esri Shapefile Folder
- SourceDataset_SHAPEFILE = C:\Users\eliza\Desktop\Dane_obszary_badawcze\esri\Placemark.shp   # Source Esri Shapefile(s)
- SourceDataset_SHAPEFILE_6 = C:\Users\eliza\Desktop\Dane_obszary_badawcze\esri\inne\Style.shp   # Source Esri Shapefile(s)
- SourceDataset_GEOTIFF = C:\Users\eliza\Desktop\Landsat_5\p186r025_4dt19880727_z34_10.tif   # Source GeoTIFF File(s)
- SourceDataset_PATH_11 = C:\Users\eliza\Desktop\p3   # Source Folder and File Pathnames Folder
- SourceDataset_PATH_8 = C:\Users\eliza\Desktop\p4   # Source Folder and File Pathnames Folder
- SourceDataset_PATH_10 = C:\Users\eliza\Desktop\Dane_obszary_badawcze   # Source Folder and File Pathnames Folder
- SourceDataset_SHAPEFILE_9 = C:\Users\eliza\Desktop\Dane_obszary_badawcze_shapefile\esri\Placemark.shp   # Source Esri Shapefile(s)
- DestDataset_GEOTIFF = C:\Users\eliza\Desktop\Landsat5_clipped   # Destination GeoTIFF Folder
- DatasetsDirPath = D:\FME_data\cloudless\for_calculations   # Path of directory with datasets
- OutputDirectory = D:\FME\Output   # Path to output directory
- DestDataset_GEOTIFF_2 = C:\Users\eliza\Desktop\Landsat5_clipped   # Destination GeoTIFF Folder
- DestDataset_GEOTIFF_3 = C:\Users\eliza\Desktop\Landsat5_clipped   # Destination GeoTIFF Folder
- SourceDataset_PATH_12 = C:\Users\eliza\Desktop\Landsat5_clipped   # Source Folder and File Pathnames Folder
- SourceDataset_SHAPEFILE_7 = C:\Users\eliza\Desktop\Dane_obszary_badawcze\esri\Document.shp   # Source Esri Shapefile(s)
- SourceDataset_SHAPEFILE_8 = C:\Users\eliza\Desktop\Dane_obszary_badawcze_shapefile\Placemark.shp   # Source Esri Shapefile(s)
- DestDataset_GEOTIFF_4 = C:\Users\eliza\Desktop\Landsat5_NDVI   # Destination GeoTIFF Folder
- DestDataset_GEOTIFF_10 = C:\Users\eliza\Desktop\Cloud Detection\Cloudless files\Drugie   # Destination GeoTIFF Folder
- SourceDataset_JPEG2000 = C:\Users\eliza\Desktop\Cloud Detection\pierwsze.jp2   # Source JPEG 2000 File(s)
- SourceDataset_GEOTIFF_11 = C:\Users\eliza\Desktop\Cloud Detection\Cloudless files\clouds_prob.tif   # Source GeoTIFF File(s)
- SourceDataset_GEOTIFF_17 = C:\Users\eliza\Desktop\Cloud Detection\Cloudless files\GEOTIFF.tif   # Source GeoTIFF File(s)
- SourceDataset_GEOTIFF_16 = C:\Users\eliza\Desktop\Cloud Detection\Cloudless files\clouds_prob.tif   # Source GeoTIFF File(s)
- SourceDataset_PNGRASTER = C:\Users\eliza\Desktop\Cloud Detection\drugie.PNG   # Source PNG (Portable Network Graphics) File(s)
- SourceDataset_GEOTIFF_19 = C:\Users\eliza\Desktop\Cloud Detection\Cloudless files\Drugie\clouds_prob.tif   # Source GeoTIFF File(s)
- SourceDataset_GEOTIFF_12 = C:\Users\eliza\Desktop\p3\p186r025_4dt19880727_z34_30.tif   # Source GeoTIFF File(s)
- SourceDataset_GEOTIFF_13 = C:\Users\eliza\Desktop\p4\p186r025_4dt19880727_z34_40.tif   # Source GeoTIFF File(s)
- SourceDataset_GEOTIFF_14 = C:\Users\eliza\Desktop\Cloud Detection\Cloudless files\Drugie\clouds.tif   # Source GeoTIFF File(s)
- SourceDataset_GEOTIFF_15 = C:\Users\eliza\Desktop\Cloud Detection\Cloudless files\GEOTIFF.tif   # Source GeoTIFF File(s)
- SourceDataset_GEOTIFF_18 = C:\Users\eliza\Desktop\Cloud Detection\pierwsze_tif.tif   # Source GeoTIFF File(s)
- DestDataset_GEOTIFF_5 = C:\Users\eliza\Desktop\Cloud Detection   # Destination GeoTIFF Folder
- DestDataset_GEOTIFF_6 = C:\Users\eliza\Desktop\Cloud Detection\Cloudless files\Pierwsza_maska_zmniejszona   # Destination GeoTIFF Folder
- DestDataset_GEOTIFF_7 = C:\Users\eliza\Desktop\Cloud Detection   # Destination GeoTIFF Folder
- DestDataset_GEOTIFF_8 = C:\Users\eliza\Desktop\Cloud Detection\Cloudless files\Drugie\Druga_maska_zmniejszona   # Destination GeoTIFF Folder
- login = eliza_97

Readers:
- XLSXR_1: XLSXR from $(SourceDataset_XLSXR)
- XLSXR_2: XLSXR from $(SourceDataset_XLSXR_3)
- PATH_1: PATH from $(SourceDataset_PATH)
- PATH_2: PATH from $(SourceDataset_PATH_9)
- PATH_3: PATH from $(SourceDataset_PATH_13) in LL84
- OGCKML_1: OGCKML from $(SourceDataset_OGCKML)
- OGCKML_2: OGCKML from $(SourceDataset_OGCKML_3)
- SHAPEFILE_1: SHAPEFILE from $(SourceDataset_SHAPEFILE)
- SHAPEFILE_2: SHAPEFILE from $(SourceDataset_SHAPEFILE_7)
- SHAPEFILE_3: SHAPEFILE from $(SourceDataset_SHAPEFILE_6)
- GEOTIFF_1: GEOTIFF from $(SourceDataset_GEOTIFF)
- PATH_4: PATH from $(SourceDataset_PATH_11)
- PATH_5: PATH from $(SourceDataset_PATH_8)
- GEOTIFF_2: GEOTIFF from $(SourceDataset_GEOTIFF_12)
- GEOTIFF_3: GEOTIFF from $(SourceDataset_GEOTIFF_13)
- PATH_6: PATH from $(SourceDataset_PATH_10)
- SHAPEFILE_4: SHAPEFILE from $(SourceDataset_SHAPEFILE_8)
- SHAPEFILE_5: SHAPEFILE from $(SourceDataset_SHAPEFILE_9)
- PATH_7: PATH from $(SourceDataset_PATH_12) in LL84
- GEOTIFF_4: GEOTIFF from $(SourceDataset_GEOTIFF_14)
- JPEG2000_1: JPEG2000 from $(SourceDataset_JPEG2000)
- GEOTIFF_5: GEOTIFF from $(SourceDataset_GEOTIFF_15)
- GEOTIFF_6: GEOTIFF from $(SourceDataset_GEOTIFF_18)
- GEOTIFF_7: GEOTIFF from $(SourceDataset_GEOTIFF_11)
- GEOTIFF_8: GEOTIFF from $(SourceDataset_GEOTIFF_17)
- GEOTIFF_9: GEOTIFF from $(SourceDataset_GEOTIFF_16)
- PNGRASTER_1: PNGRASTER from $(SourceDataset_PNGRASTER)
- GEOTIFF_10: GEOTIFF from $(SourceDataset_GEOTIFF_19)

Writers:
- GEOJSON_1: GEOJSON to $(DestDataset_GEOJSON)
- XLSXW_1: XLSXW to $(DestDataset_XLSXW)
- SHAPEFILE_6: SHAPEFILE to $(DestDataset_SHAPEFILE)
- SHAPEFILE_7: SHAPEFILE to $(DestDataset_SHAPEFILE_3)
- GEOTIFF_11: GEOTIFF to $(DestDataset_GEOTIFF)
- GEOTIFF_12: GEOTIFF to $(DestDataset_GEOTIFF_2)
- GEOTIFF_13: GEOTIFF to $(DestDataset_GEOTIFF_3)
- GEOTIFF_14: GEOTIFF to $(DestDataset_GEOTIFF_4)
- GEOTIFF_15: GEOTIFF to $(DestDataset_GEOTIFF_10)
- GEOTIFF_16: GEOTIFF to $(DestDataset_GEOTIFF_5)
- GEOTIFF_17: GEOTIFF to $(DestDataset_GEOTIFF_6)
- GEOTIFF_18: GEOTIFF to $(DestDataset_GEOTIFF_7)
- GEOTIFF_19: GEOTIFF to $(DestDataset_GEOTIFF_8)

Note: Inicjalizacja
Creator_2
    GEOMTYPE = Geometry Object
    NUM = 1
    CREATED -> M2M_HTTPCaller_2
Note: Generacja klucza API
M2M_HTTPCaller_2: HTTPCaller
    AUTH_METHOD = Basic
    AUTH_PASSWORD =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
    AUTH_USERNAME = login_do_usgs
    CONNECTION_TIMEOUT_LENGTH = 600
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/login?
    TRANSFER_TIMEOUT_LENGTH = 900
    UPLOAD_BODY = { "username": "login_do_usgs", "password": "haslo_do_usgs" }
    UPLOAD_CONTENT_TYPE = JSON (application/json)
    UPLOAD_TYPE = Specify Upload Body
    USE_COOKIES = No
    VERIFY_SSL_CERTIFICATES = Yes
    -> JSONExtractor_2
Note: Wydobycie klucza API
JSONExtractor_2
    EXTRACT_QUERY_TABLE = API_key json["data"]
    JSON_DOCUMENT = @Value(_response_body)
    READ_FROM_FILE = NO
    EVALUATED -> HTTPCaller_3
    <REJECTED> -> Junction_11
Note: Search-scene LANDSAT-8
HTTPCaller_3
    AUTH_METHOD = Basic
    AUTH_PASSWORD =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
    AUTH_USERNAME = eliza_97
    CONNECTION_TIMEOUT_LENGTH = 1000
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/scene-search?
    TRANSFER_TIMEOUT_LENGTH = 1000
    UPLOAD_BODY:
      {
          "maxResults":1000,
          "datasetName": "$(datasetName_Landsat8)",
          "sceneFilter": {
              "spatialFilter": {
                  "filterType": "mbr",
                  "lowerLeft": {
                          "latitude": $(latitude_ll),
                          "longitude": $(longitude_ll)
                  },
                  "upperRight": {
                          "latitude": $(latitude_ur),
                          "longitude": $(longitude_ur)
                  }
              },
              "metadataFilter": null,
              "cloudCoverFilter": {
                  "max": $(cloudCover_max),
                  "min": 0,
                  "includeUnknown": true
              },
              "ingestFilter": {
                  "end": "$(endDate_Landsat8)",
                  "start": "$(startDate_Landsat8)"
                  }
          },
          "metadataType": "summary",
          "sortDirection": "ASC",
          "startingNumber": 1
      }
    UPLOAD_CONTENT_TYPE = JSON (application/json)
    UPLOAD_TYPE = Specify Upload Body
    USE_COOKIES = No
    VERIFY_SSL_CERTIFICATES = Yes
    -> JSONFragmenter
    <REJECTED> -> Junction_12
Note: Wydobycie entityId
JSONFragmenter
    EXPLODE_FORMAT = JSON
    EXTRACT_ATTR = Yes
    JSON_ATTR = _response_body
    JSON_QUERY = json["data"]["results"][*]["entityId"]
    READ_FROM_FILE = NO
    RECURSIVE = Yes
    REJECT_EMPTY_LISTS = YES
    FRAGMENTS -> HTTPCaller_5
Note: Scene-metadata / Sprawdzenie cloud cover dla Landsat
HTTPCaller_5
    AUTH_METHOD = Basic
    AUTH_PASSWORD =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
    AUTH_USERNAME = eliza_97
    CONNECTION_TIMEOUT_LENGTH = 600
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/scene-metadata?
    TRANSFER_TIMEOUT_LENGTH = 900
    UPLOAD_BODY:
      {
          "entityId": "@Value(_response_body)",
          "datasetName": "$(datasetName_Landsat8)"
      }
    UPLOAD_CONTENT_TYPE = JSON (application/json)
    UPLOAD_TYPE = Specify Upload Body
    USE_COOKIES = No
    VERIFY_SSL_CERTIFICATES = Yes
    -> JSONExtractor
    <REJECTED> -> Junction_14
Note: Wydobycie informacji o Cloud Cover dla danego entityId
JSONExtractor
    EXTRACT_QUERY_TABLE = Cloud_cover json["data"]["cloudCover"] Entity_Id json["data"]["entityId"] Acquisition_date json["data"]["metadata"][2]["value"] NW_corner_lat json["data"]["spatialBounds"]["coordinates"][0][1][1] NW_corner_long json["data"]["spatialBounds"]["coordinates"][0][1][0]
    JSON_DOCUMENT = @Value(_response_body)
    READ_FROM_FILE = NO
    EVALUATED -> Tester
    <REJECTED> -> Junction_13
Note: Odfiltrowanie elementow dla ktorych CC <= 15%
Tester
    BOOL_OP = AND
    COMPOSITE_TEST = 1 AND 2
    TEST_CLAUSE:
      TEST @Value(Cloud_cover) <= 15
      TEST @Value(Cloud_cover) >= 0
    TEST_MODE = TEST
    PASSED -> Tester_14
Note: Odfiltrowanie zdjec poza obszarem lesnictwa
Tester_14
    BOOL_OP = COMPOSITE
    COMPOSITE_TEST = 1 AND 2 AND 3 AND 4
    TEST_CLAUSE:
      TEST @Value(NW_corner_lat) > 50.02
      TEST @Value(NW_corner_lat) < 51.7
      TEST @Value(NW_corner_long) > 18.7
      TEST @Value(NW_corner_long) < 21.4
    TEST_MODE = TEST
    PASSED -> AttributeFileReader
Note: Odczytanie pliku z datami
AttributeFileReader
    CHAR_ENCODING = windows-1252
    DEST_ATTR = _file_contents
    FILE_NAME = $(TXT_Path_Landsat_8)
    -> SubstringExtractor
    <REJECTED> -> Junction_10
Note: Pobranie roku i miesiaca z Acqusition_date, bez dnia
SubstringExtractor
    END = 6
    RESULT_ATTR = _acq_date
    SRC_STRING = @Value(Acquisition_date)
    START = 0
    -> Tester_2
Note: Jezeli pobrany plik z danego roku i miesiaca zostal juz pobrany to go odrzuc (chcemy 1 plik na miesiac w danym roku)
Tester_2
    BOOL_OP = OR
    COMPOSITE_TEST = 1
    TEST_CLAUSE = CASE_INSENSITIVE_TEST @Value(_file_contents) NOT_CONTAINS @Value(_acq_date)
    TEST_MODE = CASE_INSENSITIVE_TEST
    PASSED -> AttributeFileReader_6
Note: Odczytanie pliku z datami
AttributeFileReader_6
    CHAR_ENCODING = windows-1252
    DEST_ATTR = _file_contents
    FILE_NAME = $(TXT_Path_Sentinel)
    -> SubstringExtractor_6
    <REJECTED> -> Junction_9
Note: Pobranie roku i miesiaca z Acqusition_date, bez dnia
SubstringExtractor_6
    END = 6
    RESULT_ATTR = _acq_date_s2
    SRC_STRING = @Value(Acquisition_date)
    START = 0
    -> Tester_20
Note: Jezeli pobrany plik z danego roku i miesiaca zostal juz pobrany to go odrzuc (chcemy 1 plik na miesiac w danym roku)
Tester_20
    BOOL_OP = OR
    COMPOSITE_TEST = 1
    TEST_CLAUSE = CASE_INSENSITIVE_TEST @Value(_file_contents) NOT_CONTAINS @Value(_acq_date_s2)
    TEST_MODE = CASE_INSENSITIVE_TEST
    PASSED -> AttributeFileReader_7
Note: Odczytanie pliku z datami
AttributeFileReader_7
    CHAR_ENCODING = windows-1252
    DEST_ATTR = _file_contents
    FILE_NAME = C:\Users\eliza\Desktop\Dane\Daty_Landsat_7.txt
    -> SubstringExtractor_7
    <REJECTED> -> Junction_18
Note: Pobranie roku i miesiaca z Acqusition_date, bez dnia
SubstringExtractor_7
    END = 6
    RESULT_ATTR = _acq_date_l7
    SRC_STRING = @Value(Acquisition_date)
    START = 0
    -> Tester_21
Note: Jezeli pobrany plik z danego roku i miesiaca zostal juz pobrany to go odrzuc (chcemy 1 plik na miesiac w danym roku)
Tester_21
    BOOL_OP = OR
    COMPOSITE_TEST = 1
    TEST_CLAUSE = CASE_INSENSITIVE_TEST @Value(_file_contents) NOT_CONTAINS @Value(_acq_date_l7)
    TEST_MODE = CASE_INSENSITIVE_TEST
    PASSED -> HTTPCaller_4
Note: Download-options, pobranie productId
HTTPCaller_4
    AUTH_METHOD = Basic
    AUTH_PASSWORD =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
    AUTH_USERNAME = eliza_97
    CONNECTION_TIMEOUT_LENGTH = 600
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/download-options?
    TRANSFER_TIMEOUT_LENGTH = 900
    UPLOAD_BODY:
      {
          "entityIds": "@Value(Entity_Id)",
          "datasetName": "$(datasetName_Landsat8)"
      }
    UPLOAD_CONTENT_TYPE = JSON (application/json)
    UPLOAD_TYPE = Specify Upload Body
    USE_COOKIES = No
    VERIFY_SSL_CERTIFICATES = Yes
    -> JSONExtractor_3
    <REJECTED> -> Junction_15
Note: Wydobycie informacji o productId
JSONExtractor_3
    EXTRACT_QUERY_TABLE = Product_Id json["data"][4]["id"]
    JSON_DOCUMENT = @Value(_response_body)
    READ_FROM_FILE = NO
    EVALUATED -> HTTPCaller_2
Note: Pobranie adresu URL do pobrania obrazow satelity
HTTPCaller_2
    AUTH_METHOD = Basic
    AUTH_PASSWORD =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
    AUTH_USERNAME = eliza_97
    CONNECTION_TIMEOUT_LENGTH = 1000
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/download-request?
    TRANSFER_TIMEOUT_LENGTH = 1000
    UPLOAD_BODY:
      {
          "downloads": [
              {
                  "label": "123456",
                  "entityId": "@Value(Entity_Id)",
                  "productId": "@Value(Product_Id)"
              }
          ],
          "downloadApplication": "EE"
      }
    UPLOAD_CONTENT_TYPE = JSON (application/json)
    UPLOAD_TYPE = Specify Upload Body
    USE_COOKIES = No
    VERIFY_SSL_CERTIFICATES = Yes
    -> JSONExtractor_5
    <REJECTED> -> Junction_16
Note: Wydobycie URL
JSONExtractor_5
    EXTRACT_QUERY_TABLE = URL_adress json["data"]["preparingDownloads"][*]["url"]
    JSON_DOCUMENT = @Value(_response_body)
    READ_FROM_FILE = NO
    EVALUATED -> HTTPCaller_6
Note: Pobranie obrazu z danego URL
HTTPCaller_6
    AUTH_METHOD = Basic
    AUTH_PASSWORD =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
    AUTH_USERNAME = eliza_97
    CONNECTION_TIMEOUT_LENGTH = 600
    CUSTOM_HEADERS = X-Auth-Token;@Value(API_key)
    ERROR_ATTR = _error
    FILE_PATH_ATTR = _response_file_path
    FOLLOW_REDIRECTS = FOLLOW_WITH_GET
    HTTP_METHOD = GET
    OUTPUT_FILENAME = C:\Users\eliza\Desktop\Landsat_8\@Value(Entity_Id).tar.gz
    REDIRECT_AUTH = UNRESTRICTED
    SAVE_FILE = File
    SAVE_MULTI = No
    STATUS_CODE_ATTR = _http_status_code
    TARGET_URL = @Value(URL_adress)
    TRANSFER_TIMEOUT_LENGTH = 900
    USE_COOKIES = No
    VERIFY_SSL_CERTIFICATES = Yes
    -> SystemCaller_3
    -> AttributeFileWriter
    <REJECTED> -> Junction_17
Note: Zapisywanie do pliiku pozyskanych dat
AttributeFileWriter
    CHAR_ENCODING = fme-system
    FILE_NAME = $(TXT_Path_Landsat_8)
    OVERWRITE_FILE = Append to file
    SOURCE_ATTR = Acquisition_date
Junction_17
Note: Wypakowanie plików cz1
SystemCaller_3
    CMD = ""C:\Program Files\7-Zip\7z.exe" e -tgzip "C:\Users\eliza\Desktop\Landsat_8.tar.gz" -o"C:\Users\eliza\Desktop\Landsat_8\@Value(Entity_Id)" -aoa"
    -> SystemCaller
Note: Wypakowanie plików cz2
SystemCaller
    CMD = ""C:\Program Files\7-Zip\7z.exe" e -ttar "C:\Users\eliza\Desktop\Landsat_8\@Value(Entity_Id)\Landsat_8.tar" -o"C:\Users\eliza\Desktop\Landsat_8" -aoa"
Junction_16
Junction_15
Junction_18
Junction_9
Junction_10
Junction_13
Junction_14
Junction_12
Junction_11
Creator
    GEOMTYPE = Geometry Object
    NUM = 1
    CREATED -> M2M_HTTPCaller_3
    CREATED -> M2M_HTTPCaller_4
    CREATED -> M2M_HTTPCaller
Note: Generacja API
M2M_HTTPCaller_3: HTTPCaller
    AUTH_METHOD = Basic
    AUTH_PASSWORD =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
    AUTH_USERNAME = login_do_usgs
    CONNECTION_TIMEOUT_LENGTH = 60
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/login?
    TRANSFER_TIMEOUT_LENGTH = 90
    UPLOAD_BODY = { "username": "login_do_usgs", "password": "haslo_do_usgs" }
    UPLOAD_CONTENT_TYPE = JSON (application/json)
    UPLOAD_TYPE = Specify Upload Body
    USE_COOKIES = No
    VERIFY_SSL_CERTIFICATES = Yes
    -> JSONExtractor_4
Note: Wydobycie informacji o productId
JSONExtractor_4
    EXTRACT_QUERY_TABLE = API_key json["data"]
    JSON_DOCUMENT = @Value(_response_body)
    READ_FROM_FILE = NO
    EVALUATED -> HTTPCaller_7
Note: Search-scene LANDSAT-7
HTTPCaller_7
    AUTH_METHOD = Basic
    AUTH_PASSWORD =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
    AUTH_USERNAME = eliza_97
    CONNECTION_TIMEOUT_LENGTH = 1000
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/scene-search?
    TRANSFER_TIMEOUT_LENGTH = 1000
    UPLOAD_BODY:
      {
          "maxResults": 2000,
          "datasetName": "$(datasetName_Landsat7)",
          "sceneFilter": {
              "spatialFilter": {
                  "filterType": "mbr",
                  "lowerLeft": {
                          "latitude": "$(latitude_ll)",
                          "longitude": "$(longitude_ll)"
                  },
                  "upperRight": {
                          "latitude": "$(latitude_ur)",
                          "longitude": "$(longitude_ur)"
                  }
              },
              "metadataFilter": null,
              "cloudCoverFilter": {
                  "max": $(cloudCover_max),
                  "min": 0,
                  "includeUnknown": true
              },
              "ingestFilter": {
                  "end": "$(endDate_Landsat7)",
                  "start": "$(startDate_Landsat7)"
                  }
          },
          "metadataType": "summary",
          "sortDirection": "ASC",
          "startingNumber": 1
      }
    UPLOAD_CONTENT_TYPE = JSON (application/json)
    UPLOAD_TYPE = Specify Upload Body
    USE_COOKIES = No
    VERIFY_SSL_CERTIFICATES = Yes
    -> JSONFragmenter_2
Note: Wydobycie entityId
JSONFragmenter_2
    EXPLODE_FORMAT = JSON
    EXTRACT_ATTR = Yes
    JSON_ATTR = _response_body
    JSON_QUERY = json["data"]["results"][*]["entityId"]
    READ_FROM_FILE = NO
    RECURSIVE = Yes
    REJECT_EMPTY_LISTS = YES
    FRAGMENTS -> HTTPCaller_8
Note: Scene-metadata / Sprawdzenie cloud cover dla Landsat
HTTPCaller_8
    AUTH_METHOD = Basic
    AUTH_PASSWORD =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
    AUTH_USERNAME = eliza_97
    CONNECTION_TIMEOUT_LENGTH = 600
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/scene-metadata?
    TRANSFER_TIMEOUT_LENGTH = 900
    UPLOAD_BODY:
      {
          "entityId": "@Value(_response_body)",
          "datasetName": "$(datasetName_Landsat7)"
      }
    UPLOAD_CONTENT_TYPE = JSON (application/json)
    UPLOAD_TYPE = Specify Upload Body
    USE_COOKIES = No
    VERIFY_SSL_CERTIFICATES = Yes
    -> JSONExtractor_6
Note: Wydobycie informacji o Cloud Cover dla danego entityId
JSONExtractor_6
    EXTRACT_QUERY_TABLE = Cloud_cover json["data"]["cloudCover"] Entity_Id json["data"]["entityId"] Acquisition_date json["data"]["metadata"][2]["value"] NW_corner_lat json["data"]["metadata"][59]["value"] NW_corner_long json["data"]["metadata"][60]["value"]
    JSON_DOCUMENT = @Value(_response_body)
    READ_FROM_FILE = NO
    EVALUATED -> Tester_3
Note: Odfiltrowanie elementow dla ktorych CC <= 15%
Tester_3
    BOOL_OP = AND
    COMPOSITE_TEST = 1 AND 2
    TEST_CLAUSE:
      TEST @Value(Cloud_cover) <= 15
      TEST @Value(Cloud_cover) >= 0
    TEST_MODE = TEST
    PASSED -> Tester_13
Note: Odfiltrowanie zdjec poza obszarem lesnictwa
Tester_13
    BOOL_OP = COMPOSITE
    COMPOSITE_TEST = 1 AND 2 AND 3 AND 4
    TEST_CLAUSE:
      TEST @Value(NW_corner_lat) > 49.6
      TEST @Value(NW_corner_lat) < 50.4
      TEST @Value(NW_corner_long) > 20.5
      TEST @Value(NW_corner_long) < 21.8
    TEST_MODE = TEST
    PASSED -> AttributeFileReader_2
Note: Odczytanie pliku z datami
AttributeFileReader_2
    CHAR_ENCODING = windows-1252
    DEST_ATTR = _file_contents
    FILE_NAME = C:\Users\eliza\Desktop\Dane\Daty_Landsat_7.txt
    -> SubstringExtractor_2
Note: Pobranie roku i miesiaca z Acqusition_date, bez dnia
SubstringExtractor_2
    END = 6
    RESULT_ATTR = _acq_date
    SRC_STRING = @Value(Acquisition_date)
    START = 0
    -> Tester_4
Note: Jezeli pobrany plik z danego roku i miesiaca zostal juz pobrany to go odrzuc (chcemy 1 plik na miesiac w danym roku)
Tester_4
    BOOL_OP = OR
    COMPOSITE_TEST = 1
    TEST_CLAUSE = CASE_INSENSITIVE_TEST @Value(_file_contents) NOT_CONTAINS @Value(_acq_date)
    TEST_MODE = CASE_INSENSITIVE_TEST
    PASSED -> HTTPCaller_10
Note: Download-options, pobranie productId
HTTPCaller_10
    AUTH_METHOD = Basic
    AUTH_PASSWORD =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
    AUTH_USERNAME = eliza_97
    CONNECTION_TIMEOUT_LENGTH = 600
    CUSTOM_HEADERS = X-Auth-Token;eyJjaWQiOjI0NTgwMTY3LCJzIjoiMTYxNDY5NTExOSIsInIiOjEzMCwicCI6WyJkb3dubG9hZCIsIm9yZGVyIl19
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/download-options?
    TRANSFER_TIMEOUT_LENGTH = 900
    UPLOAD_BODY:
      {
          "entityIds": "@Value(Entity_Id)",
          "datasetName": "$(datasetName_Landsat7)"
      }
    UPLOAD_CONTENT_TYPE = JSON (application/json)
    UPLOAD_TYPE = Specify Upload Body
    USE_COOKIES = No
    VERIFY_SSL_CERTIFICATES = Yes
    -> JSONExtractor_7
Note: Wydobycie informacji o productId
JSONExtractor_7
    EXTRACT_QUERY_TABLE = Product_Id json["data"][4]["id"]
    JSON_DOCUMENT = @Value(_response_body)
    READ_FROM_FILE = NO
    EVALUATED -> HTTPCaller_9
Note: Pobranie adresu URL do pobrania obrazow satelity
HTTPCaller_9
    AUTH_METHOD = Basic
    AUTH_PASSWORD =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
    AUTH_USERNAME = eliza_97
    CONNECTION_TIMEOUT_LENGTH = 1000
    CUSTOM_HEADERS = X-Auth-Token;eyJjaWQiOjI0NTgwMTY3LCJzIjoiMTYxNDY5NTExOSIsInIiOjEzMCwicCI6WyJkb3dubG9hZCIsIm9yZGVyIl19
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/download-request?
    TRANSFER_TIMEOUT_LENGTH = 1000
    UPLOAD_BODY:
      {
          "downloads": [
              {
                  "label": "123456",
                  "entityId": "@Value(Entity_Id)",
                  "productId": "@Value(Product_Id)"
              }
          ],
          "downloadApplication": "EE"
      }
    UPLOAD_CONTENT_TYPE = JSON (application/json)
    UPLOAD_TYPE = Specify Upload Body
    USE_COOKIES = No
    VERIFY_SSL_CERTIFICATES = Yes
    -> JSONExtractor_8
Note: Wydobycie URL
JSONExtractor_8
    EXTRACT_QUERY_TABLE = URL_adress json["data"]["preparingDownloads"][*]["url"]
    JSON_DOCUMENT = @Value(_response_body)
    READ_FROM_FILE = NO
    EVALUATED -> HTTPCaller_11
Note: Pobranie obrazu z danego URL
HTTPCaller_11
    AUTH_METHOD = Basic
    AUTH_PASSWORD =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
    AUTH_USERNAME = eliza_97
    CONNECTION_TIMEOUT_LENGTH = 600
    CUSTOM_HEADERS = X-Auth-Token;@Value(API_key)
    ERROR_ATTR = _error
    FILE_PATH_ATTR = _response_file_path
    FOLLOW_REDIRECTS = FOLLOW_WITH_GET
    HTTP_METHOD = GET
    OUTPUT_FILENAME = C:\Users\eliza\Desktop\Landsat_7.tar.gz
    REDIRECT_AUTH = UNRESTRICTED
    SAVE_FILE = File
    SAVE_MULTI = No
    STATUS_CODE_ATTR = _http_status_code
    TARGET_URL = @Value(URL_adress)
    TRANSFER_TIMEOUT_LENGTH = 900
    USE_COOKIES = No
    VERIFY_SSL_CERTIFICATES = Yes
    -> SystemCaller_4
    -> AttributeFileWriter_2
Note: Zapisywanie do pliiku pozyskanych dat
AttributeFileWriter_2
    CHAR_ENCODING = fme-system
    FILE_NAME = $(TXT_Landsat_7)
    OVERWRITE_FILE = Append to file
    SOURCE_ATTR = Acquisition_date
Note: Wypakowanie plikow .tar.gz
SystemCaller_4
    CMD = ""C:\Program Files\7-Zip\7z.exe" e -tgzip "C:\Users\eliza\Desktop\Landsat_7.tar.gz" -o"C:\Users\eliza\Desktop\Landsat_7\@Value(Entity_Id)" -aoa"
    -> SystemCaller_2
SystemCaller_2
    CMD = ""C:\Program Files\7-Zip\7z.exe" e -ttar "C:\Users\eliza\Desktop\Landsat_7\@Value(Entity_Id)\Landsat_7.tar" -o"C:\Users\eliza\Desktop\Landsat_7" -aoa"
Note: Generacja API
M2M_HTTPCaller_4: HTTPCaller
    AUTH_METHOD = Basic
    AUTH_PASSWORD =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
    AUTH_USERNAME = login_do_usgs
    CONNECTION_TIMEOUT_LENGTH = 60
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/login?
    TRANSFER_TIMEOUT_LENGTH = 90
    UPLOAD_BODY = { "username": "login_do_usgs", "password": "haslo_do_usgs" }
    UPLOAD_CONTENT_TYPE = JSON (application/json)
    UPLOAD_TYPE = Specify Upload Body
    USE_COOKIES = No
    VERIFY_SSL_CERTIFICATES = Yes
    -> JSONExtractor_9
Note: Wydobycie informacji o productId
JSONExtractor_9
    EXTRACT_QUERY_TABLE = API_key json["data"]
    JSON_DOCUMENT = @Value(_response_body)
    READ_FROM_FILE = NO
    EVALUATED -> HTTPCaller_12
Note: Search-scene LANDSAT-5
HTTPCaller_12
    AUTH_METHOD = Basic
    AUTH_PASSWORD =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
    AUTH_USERNAME = eliza_97
    CONNECTION_TIMEOUT_LENGTH = 1000
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/scene-search?
    TRANSFER_TIMEOUT_LENGTH = 1000
    UPLOAD_BODY:
      {
          "maxResults": 1000,
          "datasetName": "$(datasetName_Landsat5)",
          "sceneFilter": {
              "spatialFilter": {
                  "filterType": "mbr",
                  "lowerLeft": {
                          "latitude": $(latitude_ll),
                          "longitude": $(longitude_ll)
                  },
                  "upperRight": {
                          "latitude": $(latitude_ur),
                          "longitude": $(longitude_ur)
                  }
              },
              "metadataFilter": null,
              "cloudCoverFilter": {
                  "max": $(cloudCover_max),
                  "min": 0,
                  "includeUnknown": true
              },
              "ingestFilter": {
                  "end": "$(endDate_Landsat5)",
                  "start": "$(startDate_Landsat5)"
                  }
          },
          "metadataType": "summary",
          "sortDirection": "ASC",
          "startingNumber": 40
      }
    UPLOAD_CONTENT_TYPE = JSON (application/json)
    UPLOAD_TYPE = Specify Upload Body
    USE_COOKIES = No
    VERIFY_SSL_CERTIFICATES = Yes
    -> JSONFragmenter_3
Note: Wydobycie entityId
JSONFragmenter_3
    EXPLODE_FORMAT = JSON
    EXTRACT_ATTR = Yes
    JSON_ATTR = _response_body
    JSON_QUERY = json["data"]["results"][*]["entityId"]
    READ_FROM_FILE = NO
    RECURSIVE = Yes
    REJECT_EMPTY_LISTS = YES
    FRAGMENTS -> HTTPCaller_13
Note: Scene-metadata / Sprawdzenie cloud cover dla Landsat
HTTPCaller_13
    AUTH_METHOD = Basic
    AUTH_PASSWORD =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
    AUTH_USERNAME = eliza_97
    CONNECTION_TIMEOUT_LENGTH = 600
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/scene-metadata?
    TRANSFER_TIMEOUT_LENGTH = 900
    UPLOAD_BODY:
      {
          "entityId": "@Value(_response_body)",
          "datasetName": "$(datasetName_Landsat5)"
      }
    UPLOAD_CONTENT_TYPE = JSON (application/json)
    UPLOAD_TYPE = Specify Upload Body
    USE_COOKIES = No
    VERIFY_SSL_CERTIFICATES = Yes
    -> JSONExtractor_10
Note: Wydobycie informacji o Cloud Cover dla danego entityId
JSONExtractor_10
    EXTRACT_QUERY_TABLE = Cloud_cover json["data"]["cloudCover"] Entity_Id json["data"]["entityId"] Acquisition_date json["data"]["metadata"][1]["value"] NW_corner_lat json["data"]["metadata"][27]["value"] NW_corner_long json["data"]["metadata"][28]["value"]
    JSON_DOCUMENT = @Value(_response_body)
    READ_FROM_FILE = NO
    EVALUATED -> Tester_5
Note: Odfiltrowanie elementow dla ktorych CC <= 15%
Tester_5
    BOOL_OP = AND
    COMPOSITE_TEST = 1 AND 2
    TEST_CLAUSE:
      TEST @Value(Cloud_cover) <= 15
      TEST @Value(Cloud_cover) >= 0
    TEST_MODE = TEST
    PASSED -> Tester_12
Note: Odfiltrowanie zdjec poza obszarem lesnictwa
Tester_12
    BOOL_OP = COMPOSITE
    COMPOSITE_TEST = 1 AND 2 AND 3 AND 4
    TEST_CLAUSE:
      TEST @Value(NW_corner_lat) > 49.6
      TEST @Value(NW_corner_lat) < 50.4
      TEST @Value(NW_corner_long) > 20.5
      TEST @Value(NW_corner_long) < 21.8
    TEST_MODE = TEST
    PASSED -> AttributeFileReader_3
Note: Odczytanie pliku z datami
AttributeFileReader_3
    CHAR_ENCODING = windows-1252
    DEST_ATTR = _file_contents
    FILE_NAME = C:\Users\eliza\Desktop\Dane\Daty_Landsat_5.txt
    -> SubstringExtractor_3
Note: Pobranie roku i miesiaca z Acqusition_date, bez dnia
SubstringExtractor_3
    END = 6
    RESULT_ATTR = _acq_date
    SRC_STRING = @Value(Acquisition_date)
    START = 0
    -> Tester_6
Note: Jezeli pobrany plik z danego roku i miesiaca zostal juz pobrany to go odrzuc (chcemy 1 plik na miesiac w danym roku)
Tester_6
    BOOL_OP = OR
    COMPOSITE_TEST = 1
    TEST_CLAUSE = CASE_INSENSITIVE_TEST @Value(_file_contents) NOT_CONTAINS @Value(_acq_date)
    TEST_MODE = CASE_INSENSITIVE_TEST
    PASSED -> Tester_9
Note: Sprawdzenie daty akwizycji
Tester_9
    BOOL_OP = OR
    COMPOSITE_TEST = 1
    TEST_CLAUSE = TEST @Value(Acquisition_date) NOT_< 1999-01-01
    TEST_MODE = TEST
    PASSED -> HTTPCaller_15
Note: Download-options, pobranie productId
HTTPCaller_15
    AUTH_METHOD = Basic
    AUTH_PASSWORD =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
    AUTH_USERNAME = eliza_97
    CONNECTION_TIMEOUT_LENGTH = 600
    CUSTOM_HEADERS = X-Auth-Token;eyJjaWQiOjI0NTgwMTY3LCJzIjoiMTYxNDY5NTExOSIsInIiOjEzMCwicCI6WyJkb3dubG9hZCIsIm9yZGVyIl19
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/download-options?
    TRANSFER_TIMEOUT_LENGTH = 900
    UPLOAD_BODY:
      {
          "entityIds": "@Value(Entity_Id)",
          "datasetName": "$(datasetName_Landsat5)"
      }
    UPLOAD_CONTENT_TYPE = JSON (application/json)
    UPLOAD_TYPE = Specify Upload Body
    USE_COOKIES = No
    VERIFY_SSL_CERTIFICATES = Yes
    -> JSONExtractor_11
Note: Wydobycie informacji o productId
JSONExtractor_11
    EXTRACT_QUERY_TABLE = Product_Id json["data"][3]["id"]
    JSON_DOCUMENT = @Value(_response_body)
    READ_FROM_FILE = NO
    EVALUATED -> HTTPCaller_14
Note: Pobranie adresu URL do pobrania obrazow satelity
HTTPCaller_14
    AUTH_METHOD = Basic
    AUTH_PASSWORD =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
    AUTH_USERNAME = eliza_97
    CONNECTION_TIMEOUT_LENGTH = 1000
    CUSTOM_HEADERS = X-Auth-Token;eyJjaWQiOjI0NTgwMTY3LCJzIjoiMTYxNDY5NTExOSIsInIiOjEzMCwicCI6WyJkb3dubG9hZCIsIm9yZGVyIl19
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/download-request?
    TRANSFER_TIMEOUT_LENGTH = 1000
    UPLOAD_BODY:
      {
          "downloads": [
              {
                  "label": "123456",
                  "entityId": "@Value(Entity_Id)",
                  "productId": "@Value(Product_Id)"
              }
          ],
          "downloadApplication": "EE"
      }
    UPLOAD_CONTENT_TYPE = JSON (application/json)
    UPLOAD_TYPE = Specify Upload Body
    USE_COOKIES = No
    VERIFY_SSL_CERTIFICATES = Yes
    -> JSONExtractor_12
Note: Wydobycie URL
JSONExtractor_12
    EXTRACT_QUERY_TABLE = URL_adress json["data"]["preparingDownloads"][*]["url"]
    JSON_DOCUMENT = @Value(_response_body)
    READ_FROM_FILE = NO
    EVALUATED -> HTTPCaller_16
Note: Pobranie obrazu z danego URL
HTTPCaller_16
    AUTH_METHOD = Basic
    AUTH_PASSWORD =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
    AUTH_USERNAME = eliza_97
    CONNECTION_TIMEOUT_LENGTH = 600
    CUSTOM_HEADERS = X-Auth-Token;@Value(API_key)
    ERROR_ATTR = _error
    FILE_PATH_ATTR = _response_file_path
    FOLLOW_REDIRECTS = FOLLOW_WITH_GET
    HTTP_METHOD = GET
    OUTPUT_FILENAME = $(ZIP_Path_Landsat5)
    REDIRECT_AUTH = UNRESTRICTED
    SAVE_FILE = File
    SAVE_MULTI = No
    STATUS_CODE_ATTR = _http_status_code
    TARGET_URL = @Value(URL_adress)
    TRANSFER_TIMEOUT_LENGTH = 900
    USE_COOKIES = No
    VERIFY_SSL_CERTIFICATES = Yes
    -> AttributeFileWriter_3
    -> SystemCaller_6
Note: Zapisywanie do pliiku pozyskanych dat
AttributeFileWriter_3
    CHAR_ENCODING = fme-system
    FILE_NAME = C:\Users\eliza\Desktop\Dane\Daty_Landsat_5.txt
    OVERWRITE_FILE = Append to file
    SOURCE_ATTR = Acquisition_date
Note: Wypakowanie plikow .tar.gz
SystemCaller_6
    CMD = ""C:\Program Files\7-Zip\7z.exe" e -tgzip "C:\Users\eliza\Desktop\Landsat_5.tar.gz" -o"C:\Users\eliza\Desktop\Landsat_5\@Value(Entity_Id)" -aoa"
    -> SystemCaller_5
SystemCaller_5
    CMD = ""C:\Program Files\7-Zip\7z.exe" e -ttar "C:\Users\eliza\Desktop\Landsat_5\@Value(Entity_Id)\Landsat_5.tar" -o"C:\Users\eliza\Desktop\Landsat_5" -aoa"
Note: Generacja API
M2M_HTTPCaller: HTTPCaller
    AUTH_METHOD = Basic
    AUTH_PASSWORD =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
    AUTH_USERNAME = login_do_usgs
    CONNECTION_TIMEOUT_LENGTH = 60
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/login?
    TRANSFER_TIMEOUT_LENGTH = 90
    UPLOAD_BODY = { "username": "login_do_usgs", "password": "haslo_do_usgs" }
    UPLOAD_CONTENT_TYPE = JSON (application/json)
    UPLOAD_TYPE = Specify Upload Body
    USE_COOKIES = No
    VERIFY_SSL_CERTIFICATES = Yes
    -> JSONExtractor_16
Note: Wydobycie informacji o API
JSONExtractor_16
    EXTRACT_QUERY_TABLE = API_key json["data"]
    JSON_DOCUMENT = @Value(_response_body)
    READ_FROM_FILE = NO
    EVALUATED -> HTTPCaller_17
Note: Search-scene
HTTPCaller_17
    AUTH_METHOD = Basic
    AUTH_PASSWORD =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
    AUTH_USERNAME = eliza_97
    CONNECTION_TIMEOUT_LENGTH = 60
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/scene-search?
    TRANSFER_TIMEOUT_LENGTH = 90
    UPLOAD_BODY:
      {
          "maxResults": 5000,
          "datasetName": "$(datasetName_Sentinel2)",
          "sceneFilter": {
              "spatialFilter": {
                  "filterType": "mbr",
                  "lowerLeft": {
                          "latitude": $(latitude_ll),
                          "longitude": $(longitude_ll)
                  },
                  "upperRight": {
                          "latitude": $(latitude_ur),
                          "longitude": $(longitude_ur)
                  }
              },
              "metadataFilter": null,
              "cloudCoverFilter": {
                  "max": $(cloudCover_max),
                  "min": 0,
                  "includeUnknown": true
              },
              "ingestFilter": {
                  "end": "$(endDate_sentinel)",
                  "start": "$(startDate_sentinel)"
              }
          },
          "metadataType": "summary",
          "sortDirection": "ASC",
          "startingNumber": 400
      }
    UPLOAD_CONTENT_TYPE = JSON (application/json)
    UPLOAD_TYPE = Specify Upload Body
    USE_COOKIES = No
    VERIFY_SSL_CERTIFICATES = Yes
    -> JSONFragmenter_4
Note: Wydobycie entityId
JSONFragmenter_4
    EXPLODE_FORMAT = JSON
    EXTRACT_ATTR = Yes
    JSON_ATTR = _response_body
    JSON_QUERY = json["data"]["results"][*]["entityId"]
    READ_FROM_FILE = NO
    RECURSIVE = Yes
    REJECT_EMPTY_LISTS = YES
    FRAGMENTS -> HTTPCaller_20
Note: Scene-metadata / Sprawdzenie cloud cover dla Sentinel
HTTPCaller_20
    AUTH_METHOD = Basic
    AUTH_PASSWORD =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
    AUTH_USERNAME = eliza_97
    CONNECTION_TIMEOUT_LENGTH = 600
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/scene-metadata?
    TRANSFER_TIMEOUT_LENGTH = 900
    UPLOAD_BODY:
      {
          "entityId": "@Value(_response_body)",
          "datasetName": "$(datasetName_Sentinel2)"
      }
    UPLOAD_CONTENT_TYPE = JSON (application/json)
    UPLOAD_TYPE = Specify Upload Body
    USE_COOKIES = No
    VERIFY_SSL_CERTIFICATES = Yes
    -> JSONExtractor_13
    <REJECTED> -> Junction_2
Note: Wydobycie informacji o Cloud Cover dla danego entityId oraz wspolrzedne NW
JSONExtractor_13
    EXTRACT_QUERY_TABLE = Cloud_cover json["data"]["metadata"][4]["value"] Entity_id json["data"]["entityId"] Acquisition_date json["data"]["metadata"][1]["value"] NW_corner_lat json["data"]["metadata"][43]["value"] NW_corner_long json["data"]["metadata"][44]["value"]
    JSON_DOCUMENT = @Value(_response_body)
    READ_FROM_FILE = NO
    EVALUATED -> Tester_7
Note: Odfiltrowanie elementow dla ktorych CC <= 15%
Tester_7
    BOOL_OP = AND
    COMPOSITE_TEST = 1 AND 2
    TEST_CLAUSE:
      TEST @Value(Cloud_cover) <= 15
      TEST @Value(Cloud_cover) >= 0
    TEST_MODE = TEST
    PASSED -> Tester_11
Note: Odfiltrowanie zdjec poza obszarem lesnictwa
Tester_11
    BOOL_OP = COMPOSITE
    COMPOSITE_TEST = 1 AND 2 AND 3 AND 4
    TEST_CLAUSE:
      TEST @Value(NW_corner_lat) > 49.6
      TEST @Value(NW_corner_lat) < 50.4
      TEST @Value(NW_corner_long) > 20.5
      TEST @Value(NW_corner_long) < 21.8
    TEST_MODE = TEST
    PASSED -> AttributeFileReader_4
Note: Odczytanie pliku z datami
AttributeFileReader_4
    CHAR_ENCODING = windows-1252
    DEST_ATTR = _file_contents
    FILE_NAME = $(TXT_Path_Sentinel)
    -> SubstringExtractor_4
Note: Pobranie roku i miesiaca z Acqusition_date, bez dnia
SubstringExtractor_4
    END = 6
    RESULT_ATTR = _acq_date
    SRC_STRING = @Value(Acquisition_date)
    START = 0
    -> Tester_8
Note: Jezeli pobrany plik z danego roku i miesiaca zostal juz pobrany to go odrzuc (chcemy 1 plik na miesiac w danym roku)
Tester_8
    BOOL_OP = OR
    COMPOSITE_TEST = 1
    TEST_CLAUSE = CASE_INSENSITIVE_TEST @Value(_file_contents) NOT_CONTAINS @Value(_acq_date)
    TEST_MODE = CASE_INSENSITIVE_TEST
    PASSED -> Tester_15
Tester_15
    BOOL_OP = OR
    COMPOSITE_TEST = 1
    TEST_CLAUSE = TEST @Value(Entity_id) != 154484
    TEST_MODE = TEST
    PASSED -> HTTPCaller_19
Note: Download-options, pobranie productId
HTTPCaller_19
    AUTH_METHOD = Basic
    AUTH_PASSWORD =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
    AUTH_USERNAME = eliza_97
    CONNECTION_TIMEOUT_LENGTH = 60
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/download-options?
    TRANSFER_TIMEOUT_LENGTH = 90
    UPLOAD_BODY:
      {
          "entityIds": "@Value(Entity_id)",
          "datasetName": "$(datasetName_Sentinel2)"
      }
    UPLOAD_CONTENT_TYPE = JSON (application/json)
    UPLOAD_TYPE = Specify Upload Body
    USE_COOKIES = No
    VERIFY_SSL_CERTIFICATES = Yes
    -> JSONExtractor_14
    <REJECTED> -> Junction_3
Note: Wydobycie informacji o productId
JSONExtractor_14
    EXTRACT_QUERY_TABLE = Product_Id json["data"][0]["id"]
    JSON_DOCUMENT = @Value(_response_body)
    READ_FROM_FILE = NO
    EVALUATED -> HTTPCaller_18
Note: Pobranie adresu URL do pobrania obrazow satelity
HTTPCaller_18
    AUTH_METHOD = Basic
    AUTH_PASSWORD =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
    AUTH_USERNAME = eliza_97
    CONNECTION_TIMEOUT_LENGTH = 60
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/download-request?
    TRANSFER_TIMEOUT_LENGTH = 90
    UPLOAD_BODY:
      {
          "downloads": [
              {
                  "label": "123456",
                  "entityId": @Value(Entity_id),
                  "productId": "@Value(Product_Id)"
              }
          ],
          "downloadApplication": "EE"
      }
    UPLOAD_CONTENT_TYPE = JSON (application/json)
    UPLOAD_TYPE = Specify Upload Body
    USE_COOKIES = No
    VERIFY_SSL_CERTIFICATES = Yes
    -> JSONExtractor_15
    <REJECTED> -> Junction_4
Note: Wydobycie URL
JSONExtractor_15
    EXTRACT_QUERY_TABLE = URL_adress json["data"]["preparingDownloads"][*]["url"]
    JSON_DOCUMENT = @Value(_response_body)
    READ_FROM_FILE = NO
    EVALUATED -> HTTPCaller_21
Note: Pobranie obrazu z danego URL
HTTPCaller_21
    AUTH_METHOD = Basic
    AUTH_PASSWORD =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
    AUTH_USERNAME = eliza_97
    CONNECTION_TIMEOUT_LENGTH = 4000
    CUSTOM_HEADERS = X-Auth-Token;@Value(API_key)
    ERROR_ATTR = _error
    FILE_PATH_ATTR = _response_file_path
    FOLLOW_REDIRECTS = FOLLOW_WITH_GET
    HTTP_METHOD = GET
    OUTPUT_FILENAME = $(ZIP_Path_Sentinel)
    REDIRECT_AUTH = UNRESTRICTED
    SAVE_FILE = File
    SAVE_MULTI = No
    STATUS_CODE_ATTR = _http_status_code
    TARGET_URL = @Value(URL_adress)
    TRANSFER_TIMEOUT_LENGTH = 4000
    USE_COOKIES = No
    VERIFY_SSL_CERTIFICATES = Yes
    -> FilenamePartExtractor
    -> AttributeFileWriter_4
    <REJECTED> -> Junction
Note: Zapisywanie do pliiku pozyskanych dat
AttributeFileWriter_4
    CHAR_ENCODING = fme-system
    FILE_NAME = $(TXT_Path_Sentinel)
    OVERWRITE_FILE = Append to file
    SOURCE_ATTR = Acquisition_date
FilenamePartExtractor
    DIRNAME_ATTR = _dirname
    DIRPATH_ATTR = _dirpath
    EXTENSION_ATTR = _extension
    FULLNAME_ATTR = _filename
    ROOTNAME_ATTR = _rootname
    SRC_ATTR = @Value(_response_file_path)
    -> SystemCaller_7
Note: Wypakowanie plikow .tar.gz
SystemCaller_7
    CMD = ""C:\Program Files\7-Zip\7z.exe" e -tzip "C:\Users\eliza\Desktop\Sentinel_2.zip" -o"C:\Users\eliza\Desktop\Sentinel_2" -aoa"
Junction
Junction_4
Junction_3
Junction_2

FME custom transformer Landsat-8_downloader

Parameters:
- cloudCover_max = 15
- datasetName_Sentinel2 = lpcs_sentinel_2a
- latitude_ll = 49.4975
- longitude_ll = 21.6097
- latitude_ur = 50.0017
- longitude_ur = 22.7891
- startDate_sentinel = 2015-07-04
- endDate_sentinel = 2021-02-01
- datasetName_Landsat8 = lsr_landsat_8_c1
- startDate_Landsat8 = 2013-02-11
- endDate_Landsat8 = 2021-02-01
- ZIP_Path_Landsat8 = C:\Users\eliza\Desktop\Landsat_8.zip
- TXT_Path_Sentinel = C:\Users\eliza\Desktop\Dane\Daty_Sentinel.txt
- TXT_Path_Landsat8 = C:\Users\eliza\Desktop\Dane\Daty_Landsat_8.txt

Input (input)
    -> M2M_HTTPCaller
Note: Generacja API
M2M_HTTPCaller: HTTPCaller
    AUTH_METHOD = Basic
    AUTH_PASSWORD =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
    AUTH_USERNAME = eliza_97
    CONNECTION_TIMEOUT_LENGTH = 60
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/login?
    TRANSFER_TIMEOUT_LENGTH = 90
    UPLOAD_BODY = { "username": "eliza_97", "password": "Piry-zyle-12" }
    UPLOAD_CONTENT_TYPE = JSON (application/json)
    UPLOAD_TYPE = Specify Upload Body
    USE_COOKIES = No
    VERIFY_SSL_CERTIFICATES = Yes
    -> JSONExtractor_4
Note: Wydobycie informacji o productId
JSONExtractor_4
    EXTRACT_QUERY_TABLE = API_key json["data"]
    JSON_DOCUMENT = @Value(_response_body)
    READ_FROM_FILE = NO
    EVALUATED -> HTTPCaller_3
Note: Search-scene
HTTPCaller_3
    AUTH_METHOD = Basic
    AUTH_PASSWORD =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
    AUTH_USERNAME = eliza_97
    CONNECTION_TIMEOUT_LENGTH = 1000
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/scene-search?
    TRANSFER_TIMEOUT_LENGTH = 1000
    UPLOAD_BODY:
      {
          "maxResults": 1,
          "datasetName": "$(datasetName_Landsat8)",
          "sceneFilter": {
              "spatialFilter": {
                  "filterType": "mbr",
                  "lowerLeft": {
                          "latitude": $(latitude_ll),
                          "longitude": $(longitude_ll)
                  },
                  "upperRight": {
                          "latitude": $(latitude_ur),
                          "longitude": $(longitude_ur)
                  }
              },
              "metadataFilter": null,
              "cloudCoverFilter": {
                  "max": $(cloudCover_max),
                  "min": 0,
                  "includeUnknown": true
              },
              "ingestFilter": {
                  "end": "$(endDate_Landsat8)",
                  "start": "$(startDate_Landsat8)"
                  }
          },
          "metadataType": "summary",
          "sortDirection": "ASC",
          "startingNumber": 1
      }
    UPLOAD_CONTENT_TYPE = JSON (application/json)
    UPLOAD_TYPE = Specify Upload Body
    USE_COOKIES = No
    VERIFY_SSL_CERTIFICATES = Yes
    -> JSONFragmenter
Note: Wydobycie entityId
JSONFragmenter
    EXPLODE_FORMAT = JSON
    EXTRACT_ATTR = Yes
    JSON_ATTR = _response_body
    JSON_QUERY = json["data"]["results"][*]["entityId"]
    READ_FROM_FILE = NO
    RECURSIVE = Yes
    REJECT_EMPTY_LISTS = YES
    FRAGMENTS -> HTTPCaller_5
Note: Scene-metadata / Sprawdzenie cloud cover dla Landsat
HTTPCaller_5
    AUTH_METHOD = Basic
    AUTH_PASSWORD =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
    AUTH_USERNAME = eliza_97
    CONNECTION_TIMEOUT_LENGTH = 600
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/scene-metadata?
    TRANSFER_TIMEOUT_LENGTH = 900
    UPLOAD_BODY:
      {
          "entityId": "@Value(_response_body)",
          "datasetName": "$(datasetName_Landsat8)"
      }
    UPLOAD_CONTENT_TYPE = JSON (application/json)
    UPLOAD_TYPE = Specify Upload Body
    USE_COOKIES = No
    VERIFY_SSL_CERTIFICATES = Yes
    -> JSONExtractor
Note: Wydobycie informacji o Cloud Cover dla danego entityId
JSONExtractor
    EXTRACT_QUERY_TABLE = Cloud_cover json["data"]["cloudCover"] Entity_Id json["data"]["entityId"] Acquisition_date json["data"]["metadata"][2]["value"]
    JSON_DOCUMENT = @Value(_response_body)
    READ_FROM_FILE = NO
    EVALUATED -> Tester
Note: Odfiltrowanie elementow dla ktorych CC <= 15%
Tester
    BOOL_OP = OR
    COMPOSITE_TEST = 1
    TEST_CLAUSE = TEST @Value(Cloud_cover) <= 15
    TEST_MODE = TEST
    PASSED -> AttributeFileReader
Note: Odczytanie pliku z datami
AttributeFileReader
    CHAR_ENCODING = windows-1252
    DEST_ATTR = _file_contents
    FILE_NAME = $(TXT_Path_Landsat8)
    -> SubstringExtractor
Note: Pobranie roku i miesiaca z Acqusition_date, bez dnia
SubstringExtractor
    END = 6
    RESULT_ATTR = _acq_date
    SRC_STRING = @Value(Acquisition_date)
    START = 0
    -> Tester_2
Note: Jezeli pobrany plik z danego roku i miesiaca zostal juz pobrany to go odrzuc (chcemy 1 plik na miesiac w danym roku)
Tester_2
    BOOL_OP = OR
    COMPOSITE_TEST = 1
    TEST_CLAUSE = CASE_INSENSITIVE_TEST @Value(_file_contents) NOT_CONTAINS @Value(Acquisition_date)
    TEST_MODE = CASE_INSENSITIVE_TEST
    PASSED -> HTTPCaller_4
Note: Download-options, pobranie productId
HTTPCaller_4
    AUTH_METHOD = Basic
    AUTH_PASSWORD =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
    AUTH_USERNAME = eliza_97
    CONNECTION_TIMEOUT_LENGTH = 600
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/download-options?
    TRANSFER_TIMEOUT_LENGTH = 900
    UPLOAD_BODY:
      {
          "entityIds": "@Value(Entity_Id)",
          "datasetName": "$(datasetName_Landsat8)"
      }
    UPLOAD_CONTENT_TYPE = JSON (application/json)
    UPLOAD_TYPE = Specify Upload Body
    USE_COOKIES = No
    VERIFY_SSL_CERTIFICATES = Yes
    -> JSONExtractor_2
Note: Wydobycie informacji o productId
JSONExtractor_2
    EXTRACT_QUERY_TABLE = Product_Id json["data"][4]["id"]
    JSON_DOCUMENT = @Value(_response_body)
    READ_FROM_FILE = NO
    EVALUATED -> HTTPCaller_2
Note: Pobranie adresu URL do pobrania obrazow satelity
HTTPCaller_2
    AUTH_METHOD = Basic
    AUTH_PASSWORD =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
    AUTH_USERNAME = eliza_97
    CONNECTION_TIMEOUT_LENGTH = 1000
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/download-request?
    TRANSFER_TIMEOUT_LENGTH = 1000
    UPLOAD_BODY:
      {
          "downloads": [
              {
                  "label": "123456",
                  "entityId": "@Value(Entity_Id)",
                  "productId": "@Value(Product_Id)"
              }
          ],
          "downloadApplication": "EE"
      }
    UPLOAD_CONTENT_TYPE = JSON (application/json)
    UPLOAD_TYPE = Specify Upload Body
    USE_COOKIES = No
    VERIFY_SSL_CERTIFICATES = Yes
    -> JSONExtractor_3
Note: Wydobycie URL
JSONExtractor_3
    EXTRACT_QUERY_TABLE = URL_adress json["data"]["preparingDownloads"][*]["url"]
    JSON_DOCUMENT = @Value(_response_body)
    READ_FROM_FILE = NO
    EVALUATED -> HTTPCaller_6
Note: Pobranie obrazu z danego URL
HTTPCaller_6
    AUTH_METHOD = Basic
    AUTH_PASSWORD =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
    AUTH_USERNAME = eliza_97
    CONNECTION_TIMEOUT_LENGTH = 600
    CUSTOM_HEADERS = X-Auth-Token;@Value(API_key)
    ERROR_ATTR = _error
    FILE_PATH_ATTR = _response_file_path
    FOLLOW_REDIRECTS = FOLLOW_WITH_GET
    HTTP_METHOD = GET
    OUTPUT_FILENAME = $(ZIP_Path_Landsat8)
    REDIRECT_AUTH = UNRESTRICTED
    SAVE_FILE = File
    SAVE_MULTI = No
    STATUS_CODE_ATTR = _http_status_code
    TARGET_URL = @Value(URL_adress)
    TRANSFER_TIMEOUT_LENGTH = 900
    USE_COOKIES = No
    VERIFY_SSL_CERTIFICATES = Yes
    -> FilenamePartExtractor
    -> AttributeFileWriter
Note: Zapisywanie do pliiku pozyskanych dat
AttributeFileWriter
    CHAR_ENCODING = fme-system
    FILE_NAME = $(TXT_Path_Landsat8)
    OVERWRITE_FILE = Append to file
    SOURCE_ATTR = Acquisition_date
FilenamePartExtractor
    DIRNAME_ATTR = _dirname
    DIRPATH_ATTR = _dirpath
    EXTENSION_ATTR = _extension
    FULLNAME_ATTR = _filename
    ROOTNAME_ATTR = _rootname
    SRC_ATTR = @Value(_response_file_path)
    -> ZipExtractor
Note: Wypakowanie plikow
ZipExtractor
    PRESERVE = No
    RECURSIVE = No
    REPLACE = No
    ROOT_FOLDER = @Value(_dirpath)
    ZIP_PATH = @Value(_response_body)
    File -> FeatureReader_2 [INITIATOR]
FeatureReader_2
    ATTR_ACCUM_MODE = Only Use Result
    COMBINE_GEOM = Use Result
    DATASET = @Value(path_unix)
    FORMAT = JPEG2000
    INTERACT = <No Spatial Filter>
    JPEG2000_COMPRESSION_CACHE_SIZE_CALCULATION = AUTO
    JPEG2000_GROUP_BY_DATASET = No
    JPEG2000_PREFER_FILE_CS_UNITS = Yes
    JPEG2000_READER_META_ATTRIBUTES = fme_dataset fme_basename
    JPEG2000_READ_OFFSETS_IN_CS_UNITS = No
    JPEG2000_USE_SEARCH_ENVELOPE = NO
    OUTPUT_FEATURES_DISPLAY = Schema and Data Features
    <SCHEMA> -> TestFilter
Note: Posegregowanie bandami
TestFilter
    DEFAULT_VALUE = <UNFILTERED>
    TEST_LIST = "BOOL_OP,OR,COMPOSITE_TEST,""""""1"""""",TEST_CLAUSE,CASE_INSENSITIVE_TEST @Value(path_windows) CONTAINS B1.TIF",B01,"BOOL_OP,OR,COMPOSITE_TEST,""""""1"""""",TEST_CLAUSE,CASE_INSENSITIVE_TEST @Value(path_windows) CONTAINS B2.TIF",B02,"BOOL_OP,OR,COMPOSITE_TEST,""""""1"""""",TEST_CLAUSE,CASE_INSENSITIVE_TEST @Value(path_windows) CONTAINS B3.TIF",B03,"BOOL_OP,OR,COMPOSITE_TEST,""""""1"""""",TEST_CLAUSE,CASE_INSENSITIVE_TEST @Value(path_windows) CONTAINS B4.TIF",B04,"BOOL_OP,OR,COMPOSITE_TEST,""""""1"""""",TEST_CLAUSE,CASE_INSENSITIVE_TEST @Value(path_windows) CONTAINS B5.TIF",B05,"BOOL_OP,OR,COMPOSITE_TEST,""""""1"""""",TEST_CLAUSE,CASE_INSENSITIVE_TEST @Value(path_windows) CONTAINS B6.TIF",B06,"BOOL_OP,OR,COMPOSITE_TEST,""""""1"""""",TEST_CLAUSE,CASE_INSENSITIVE_TEST @Value(path_windows) CONTAINS B7.TIF",B07,"BOOL_OP,OR,COMPOSITE_TEST,""""""1"""""",TEST_CLAUSE,CASE_INSENSITIVE_TEST @Value(path_windows) CONTAINS B8.TIF",B08,"BOOL_OP,OR,COMPOSITE_TEST,""""""1"""""",TEST_CLAUSE,CASE_INSENSITIVE_TEST @Value(path_windows) CONTAINS B9.TIF",B09,"BOOL_OP,OR,COMPOSITE_TEST,""""""1"""""",TEST_CLAUSE,CASE_INSENSITIVE_TEST @Value(path_windows) CONTAINS B10.TIF",B10,"BOOL_OP,OR,COMPOSITE_TEST,""""""1"""""",TEST_CLAUSE,CASE_INSENSITIVE_TEST @Value(path_windows) CONTAINS B11.TIF",B11
    B01 -> Band_01 (output)
    B02 -> Band_2 (output)
    B03 -> Band_3 (output)
    B04 -> Band_4 (output)
    B05 -> Band_5 (output)
    B06 -> Band_6 (output)
    B07 -> Band_7 (output)
    B08 -> Band_8 (output)
    B09 -> Band_9 (output)
    B10 -> Band_10 (output)
    B11 -> Band_11 (output)
Band_01 (output)
Band_2 (output)
Band_3 (output)
Band_4 (output)
Band_5 (output)
Band_6 (output)
Band_7 (output)
Band_8 (output)
Band_9 (output)
Band_10 (output)
Band_11 (output)

FME custom transformer Sentinel_downloader
Download satellite imaginery from USGS, EarthExplorer

Parameters:
- cloudCover_max = 15
- datasetName_Sentinel2 = lpcs_sentinel_2a
- latitude_ll = 49.4975
- longitude_ll = 21.6097
- latitude_ur = 50.0017
- longitude_ur = 22.7891
- startDate_sentinel = 2015-07-04
- endDate_sentinel = 2021-02-01
- ZIP_Path_Sentinel = C:\Users\eliza\Desktop\Sentinel_2.zip
- TXT_Path_Sentinel = C:\Users\eliza\Desktop\Dane\Daty_Sentinel.txt

Input (input)
    -> M2M_HTTPCaller
Note: Generacja API
M2M_HTTPCaller: HTTPCaller
    AUTH_METHOD = Basic
    AUTH_PASSWORD =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
    AUTH_USERNAME = eliza_97
    CONNECTION_TIMEOUT_LENGTH = 60
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/login?
    TRANSFER_TIMEOUT_LENGTH = 90
    UPLOAD_BODY = { "username": "eliza_97", "password": "Piry-zyle-12" }
    UPLOAD_CONTENT_TYPE = JSON (application/json)
    UPLOAD_TYPE = Specify Upload Body
    USE_COOKIES = No
    VERIFY_SSL_CERTIFICATES = Yes
    -> JSONExtractor_4
Note: Wydobycie informacji o productId
JSONExtractor_4
    EXTRACT_QUERY_TABLE = API_key json["data"]
    JSON_DOCUMENT = @Value(_response_body)
    READ_FROM_FILE = NO
    EVALUATED -> HTTPCaller_3
Note: Search-scene
HTTPCaller_3
    AUTH_METHOD = Basic
    AUTH_PASSWORD =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
    AUTH_USERNAME = eliza_97
    CONNECTION_TIMEOUT_LENGTH = 60
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/scene-search?
    TRANSFER_TIMEOUT_LENGTH = 90
    UPLOAD_BODY:
      {
          "maxResults": 10,
          "datasetName": "$(datasetName_Sentinel2)",
          "sceneFilter": {
              "spatialFilter": {
                  "filterType": "mbr",
                  "lowerLeft": {
                          "latitude": $(latitude_ll),
                          "longitude": $(longitude_ll)
                  },
                  "upperRight": {
                          "latitude": $(latitude_ur),
                          "longitude": $(longitude_ur)
                  }
              },
              "metadataFilter": null,
              "cloudCoverFilter": {
                  "max": $(cloudCover_max),
                  "min": 0,
                  "includeUnknown": true
              },
              "ingestFilter": {
                  "end": "$(endDate_sentinel)",
                  "start": "$(startDate_sentinel) "
              }
          },
          "metadataType": "summary",
          "sortDirection": "ASC",
          "startingNumber": 1
      }
    UPLOAD_CONTENT_TYPE = JSON (application/json)
    UPLOAD_TYPE = Specify Upload Body
    USE_COOKIES = No
    VERIFY_SSL_CERTIFICATES = Yes
    -> JSONFragmenter
Note: Wydobycie entityId
JSONFragmenter
    EXPLODE_FORMAT = JSON
    EXTRACT_ATTR = Yes
    JSON_ATTR = _response_body
    JSON_QUERY = json["data"]["results"][*]["entityId"]
    READ_FROM_FILE = NO
    RECURSIVE = Yes
    REJECT_EMPTY_LISTS = YES
    FRAGMENTS -> HTTPCaller_5
Note: Scene-metadata / Sprawdzenie cloud cover dla Sentinel
HTTPCaller_5
    AUTH_METHOD = Basic
    AUTH_PASSWORD =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
    AUTH_USERNAME = eliza_97
    CONNECTION_TIMEOUT_LENGTH = 600
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/scene-metadata?
    TRANSFER_TIMEOUT_LENGTH = 900
    UPLOAD_BODY:
      {
          "entityId": "@Value(_response_body)",
          "datasetName": "$(datasetName_Sentinel2)"
      }
    UPLOAD_CONTENT_TYPE = JSON (application/json)
    UPLOAD_TYPE = Specify Upload Body
    USE_COOKIES = No
    VERIFY_SSL_CERTIFICATES = Yes
    -> JSONExtractor
Note: Wydobycie informacji o Cloud Cover dla danego entityId
JSONExtractor
    EXTRACT_QUERY_TABLE = Cloud_cover json["data"]["metadata"][4]["value"] Entity_id json["data"]["entityId"] Acquisition_date json["data"]["metadata"][1]["value"]
    JSON_DOCUMENT = @Value(_response_body)
    READ_FROM_FILE = NO
    EVALUATED -> Tester
Note: Odfiltrowanie elementow dla ktorych CC <= 15%
Tester
    BOOL_OP = OR
    COMPOSITE_TEST = 1
    TEST_CLAUSE = TEST @Value(Cloud_cover) <= 15
    TEST_MODE = TEST
    PASSED -> AttributeFileReader
Note: Odczytanie pliku z datami
AttributeFileReader
    CHAR_ENCODING = windows-1252
    DEST_ATTR = _file_contents
    FILE_NAME = $(TXT_Path_Sentinel)
    -> SubstringExtractor
Note: Pobranie roku i miesiaca z Acqusition_date, bez dnia
SubstringExtractor
    END = 6
    RESULT_ATTR = _acq_date
    SRC_STRING = @Value(Acquisition_date)
    START = 0
    -> Tester_2
Note: Jezeli pobrany plik z danego roku i miesiaca zostal juz pobrany to go odrzuc (chcemy 1 plik na miesiac w danym roku)
Tester_2
    BOOL_OP = OR
    COMPOSITE_TEST = 1
    TEST_CLAUSE = CASE_INSENSITIVE_TEST @Value(_file_contents) NOT_CONTAINS @Value(Acquisition_date)
    TEST_MODE = CASE_INSENSITIVE_TEST
    PASSED -> HTTPCaller_4
Note: Download-options, pobranie productId
HTTPCaller_4
    AUTH_METHOD = Basic
    AUTH_PASSWORD =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
    AUTH_USERNAME = eliza_97
    CONNECTION_TIMEOUT_LENGTH = 60
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/download-options?
    TRANSFER_TIMEOUT_LENGTH = 90
    UPLOAD_BODY:
      {
          "entityIds": "@Value(Entity_id)",
          "datasetName": "$(datasetName_Sentinel2)"
      }
    UPLOAD_CONTENT_TYPE = JSON (application/json)
    UPLOAD_TYPE = Specify Upload Body
    USE_COOKIES = No
    VERIFY_SSL_CERTIFICATES = Yes
    -> JSONExtractor_2
Note: Wydobycie informacji o productId
JSONExtractor_2
    EXTRACT_QUERY_TABLE = Product_Id json["data"][0]["id"]
    JSON_DOCUMENT = @Value(_response_body)
    READ_FROM_FILE = NO
    EVALUATED -> HTTPCaller_2
Note: Pobranie adresu URL do pobrania obrazow satelity
HTTPCaller_2
    AUTH_METHOD = Basic
    AUTH_PASSWORD =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
    AUTH_USERNAME = eliza_97
    CONNECTION_TIMEOUT_LENGTH = 60
    CUSTOM_HEADERS = X-Auth-Token;@Value(API_key)
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://m2m.cr.usgs.gov/api/api/json/stable/download-request?
    TRANSFER_TIMEOUT_LENGTH = 90
    UPLOAD_BODY:
      {
          "downloads": [
              {
                  "label": "123456",
                  "entityId": @Value(Entity_id),
                  "productId": "@Value(Product_Id)"
              }
          ],
          "downloadApplication": "EE"
      }
    UPLOAD_CONTENT_TYPE = JSON (application/json)
    UPLOAD_TYPE = Specify Upload Body
    USE_COOKIES = No
    VERIFY_SSL_CERTIFICATES = Yes
    -> JSONExtractor_3
Note: Wydobycie URL
JSONExtractor_3
    EXTRACT_QUERY_TABLE = URL_adress json["data"]["preparingDownloads"][*]["url"]
    JSON_DOCUMENT = @Value(_response_body)
    READ_FROM_FILE = NO
    EVALUATED -> HTTPCaller_6
Note: Pobranie obrazu z danego URL
HTTPCaller_6
    AUTH_METHOD = Basic
    AUTH_PASSWORD =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
    AUTH_USERNAME = eliza_97
    CONNECTION_TIMEOUT_LENGTH = 600
    CUSTOM_HEADERS = X-Auth-Token;@Value(API_key)
    ERROR_ATTR = _error
    FILE_PATH_ATTR = _response_file_path
    FOLLOW_REDIRECTS = FOLLOW_WITH_GET
    HTTP_METHOD = GET
    OUTPUT_FILENAME = $(ZIP_Path_Sentinel)
    REDIRECT_AUTH = UNRESTRICTED
    SAVE_FILE = File
    SAVE_MULTI = No
    STATUS_CODE_ATTR = _http_status_code
    TARGET_URL = @Value(URL_adress)
    TRANSFER_TIMEOUT_LENGTH = 900
    USE_COOKIES = No
    VERIFY_SSL_CERTIFICATES = Yes
    -> FilenamePartExtractor
    -> AttributeFileWriter
Note: Zapisywanie do pliiku pozyskanych dat
AttributeFileWriter
    CHAR_ENCODING = fme-system
    FILE_NAME = $(TXT_Path_Sentinel)
    OVERWRITE_FILE = Append to file
    SOURCE_ATTR = Acquisition_date
FilenamePartExtractor
    DIRNAME_ATTR = _dirname
    DIRPATH_ATTR = _dirpath
    EXTENSION_ATTR = _extension
    FULLNAME_ATTR = _filename
    ROOTNAME_ATTR = _rootname
    SRC_ATTR = @Value(_response_file_path)
    -> ZipExtractor
Note: Wypakowanie plikow
ZipExtractor
    PRESERVE = No
    RECURSIVE = No
    REPLACE = No
    ROOT_FOLDER = @Value(_dirpath)
    ZIP_PATH = $(ZIP_Path_Sentinel)
    File -> FeatureReader_2 [INITIATOR]
FeatureReader_2
    ATTR_ACCUM_MODE = Only Use Result
    COMBINE_GEOM = Use Result
    DATASET = @Value(path_unix)
    FORMAT = JPEG2000
    INTERACT = <No Spatial Filter>
    JPEG2000_COMPRESSION_CACHE_SIZE_CALCULATION = AUTO
    JPEG2000_GROUP_BY_DATASET = No
    JPEG2000_PREFER_FILE_CS_UNITS = Yes
    JPEG2000_READER_META_ATTRIBUTES = fme_dataset fme_basename
    JPEG2000_READ_OFFSETS_IN_CS_UNITS = No
    JPEG2000_USE_SEARCH_ENVELOPE = NO
    OUTPUT_FEATURES_DISPLAY = Schema and Data Features
    <SCHEMA> -> TestFilter
Note: Posegregowanie bandami
TestFilter
    DEFAULT_VALUE = <UNFILTERED>
    TEST_LIST = "BOOL_OP,OR,COMPOSITE_TEST,""""""1"""""",TEST_CLAUSE,CASE_INSENSITIVE_TEST @Value(path_windows) CONTAINS B01.jp2",B01,"BOOL_OP,OR,COMPOSITE_TEST,""""""1"""""",TEST_CLAUSE,CASE_INSENSITIVE_TEST @Value(path_windows) CONTAINS B02.jp2",B02,"BOOL_OP,OR,COMPOSITE_TEST,""""""1"""""",TEST_CLAUSE,CASE_INSENSITIVE_TEST @Value(path_windows) CONTAINS B03.jp2",B03,"BOOL_OP,OR,COMPOSITE_TEST,""""""1"""""",TEST_CLAUSE,CASE_INSENSITIVE_TEST @Value(path_windows) CONTAINS B04.jp2",B04,"BOOL_OP,OR,COMPOSITE_TEST,""""""1"""""",TEST_CLAUSE,CASE_INSENSITIVE_TEST @Value(path_windows) CONTAINS B05.jp2",B05,"BOOL_OP,OR,COMPOSITE_TEST,""""""1"""""",TEST_CLAUSE,CASE_INSENSITIVE_TEST @Value(path_windows) CONTAINS B06.jp2",B06,"BOOL_OP,OR,COMPOSITE_TEST,""""""1"""""",TEST_CLAUSE,CASE_INSENSITIVE_TEST @Value(path_windows) CONTAINS B07.jp2",B07,"BOOL_OP,OR,COMPOSITE_TEST,""""""1"""""",TEST_CLAUSE,CASE_INSENSITIVE_TEST @Value(path_windows) CONTAINS B08.jp2",B08,"BOOL_OP,OR,COMPOSITE_TEST,""""""1"""""",TEST_CLAUSE,CASE_INSENSITIVE_TEST @Value(path_windows) CONTAINS B08A.jp2",B08A,"BOOL_OP,OR,COMPOSITE_TEST,""""""1"""""",TEST_CLAUSE,CASE_INSENSITIVE_TEST @Value(path_windows) CONTAINS B09.jp2",B09,"BOOL_OP,OR,COMPOSITE_TEST,""""""1"""""",TEST_CLAUSE,CASE_INSENSITIVE_TEST @Value(path_windows) CONTAINS B10.jp2",B10,"BOOL_OP,OR,COMPOSITE_TEST,""""""1"""""",TEST_CLAUSE,CASE_INSENSITIVE_TEST @Value(path_windows) CONTAINS B11.jp2",B11,"BOOL_OP,OR,COMPOSITE_TEST,""""""1"""""",TEST_CLAUSE,CASE_INSENSITIVE_TEST @Value(path_windows) CONTAINS B12.jp2",B12
    B01 -> Band_01 (output)
    B02 -> Band_2 (output)
    B03 -> Band_3 (output)
    B04 -> Band_4 (output)
    B05 -> Band_5 (output)
    B06 -> Band_6 (output)
    B07 -> Band_7 (output)
    B08 -> Band_8 (output)
    B08A -> Band_08A (output)
    B09 -> Band_9 (output)
    B10 -> Band_10 (output)
    B11 -> Band_11 (output)
    B12 -> Band_12 (output)
Band_01 (output)
Band_2 (output)
Band_3 (output)
Band_4 (output)
Band_5 (output)
Band_6 (output)
Band_7 (output)
Band_8 (output)
Band_08A (output)
Band_9 (output)
Band_10 (output)
Band_11 (output)
Band_12 (output)

FME custom transformer ZipExtractor
Extracts files archived in a zip file, and then outputs features for every extracted file and directory.
    Each resulting feature has two attributes storing full path string of an extracted file/directory - 
    "path_unix"
    (UNIX style) and 
    "path_windows"
    (Windows style), and also has an attribute that indicates the depth of the file/directory in the extracted directory hierarchy - 
    "path_depth" 
    (integer starting from 1).
    The features containing file path will be output through the File port, and the features containing directory path will be output through the Directory port. 
    All the extracted files will be saved into a subfolder under the folder specified with the "Destination Root Folder" parameter. The subfolder name will be the same as the source zip file name without extension. For example, if the source zip file name is 
    "data.zip"
    and the specified root folder path is 
    "C:\root"
    , extracted files will be saved into 
    "C:\root\data"
    .
    If the same name folder exists under the specified root folder, a number will be added to the destination subfolder name as suffix to differentiate from the existing folder, by default. e.g. 
    "C:\root\data_1"
    , 
    "C:\root\data_2"
    , and so on. 
    If you set "Yes" to the "Replace Existing Destination Subfolder" parameter, the existing subfolder and all files within it will be removed, and then the destination subfolder will be created newly.
    By default, this transformer will NOT unzip zip files that are archived (nested) in the source zip file. If you set "Yes" to the "Unzip Nested Zip Files Recursively" parameter, this transformer unzips all the nested zip files recursively.
    All attributes of the input feature will be propagated to the output features, but the geometry and coordinate system will not be preserved.
    If the specified source zip file or destination root folder is invalid, the input feature will be output through the <Rejected> port.
    Note: The Unzipper (FME Hub) can also be used to unzip a zip file. The ZipExtractor may be useful if you need to specify the destination root folder and/or to unzip nested zip file(s).
Parameters
    Source Zip File
    :
    Specify a zip file that should be extracted. The zip file name has to end with the extension ".zip" (case insensitive) by default, but optionally, you can also specify any extension(s) which this transformer should attempt to extract as a zip file. See the Allowable Source/Nested Zip File Extensions parameter.
    Destination Root Folder
    :
    Specify a folder in which a subfolder containing all extracted files should be created. If you leave this parameter blank, this transformer treats the folder containing the source zip file as the destination root folder.
    All the extracted files will be saved into a subfolder under the root folder. The subfolder name will be the same as the source zip file name without extension. For example, if the source zip file name is 
    "data.zip"
    and the specified root folder path is 
    "C:\root"
    , extracted files will be saved into 
    "C:\root\data"
    .
    Replace Existing Destination Subfolder
    :
    By default, a number will be added to the destination subfolder name as suffix if the same name folder exists under the spcified root folder. e.g. 
    "C:\root\data_1"
    , 
    "C:\root\data_2"
    , and so on. If you set "Yes" to this parameter, the existing subfolder and all files within it will be removed, and then the destination subfolder will be created newly. 
    Unzip Nested Zip Files Recursively
    :
    By default, this transformer will NOT unzip zip files that are archived (nested) in the source zip file. If you set "Yes" to this parameter, this transformer unzips all the nested zip files recursively.
    Preserve Nested Zip Files
    :
    By default, zip files nested in the source zip file will be removed after unzipping them, when the "Unzip Nested Zip Files Recursively" parameter is set to "Yes". If you set "Yes" to this parameter, the nested zip files will also be preserved.
    This parameter affects the result only when the "Unzip Nested Zip Files Recursively" parameter is set to "Yes". When the "Unzip Nested Zip Files Recursively" is set to "No", nested zip files always will be preserved regardless of this parameter.
    Allowable Source/Nested Zip File Extension(s)
    :
    By default, this transformer accepts only zip files whose name end with the extension ".zip" (case insensitive). However, if you want to extract zip files with other extension, you can specify allowable extention(s) via these parameters, with space-separated format when specifying two or more.
    Here, "Source Zip File" means that the top level zip file which would be set to the Source Zip File parameter; "Nested Zip File"means that internal zip file(s) which have been archived within the source zip file.
    If you leave the parameter field blank (it's the default), only ".zip" (case insensitive) will be allowable as zip file extension.
    Note that "zip" won't be allowable if you have set one or more extension other than ".zip" to the parameter. If you want to allow ".zip" and other extension(s) simultaneously, specify all possible extensions including ".zip" with the parameter.
    The leading dot "." of extensions can be omitted.

Parameters:
- ZIP_PATH =   # Source Zip File
- ROOT_FOLDER =   # Destination Root Folder
- REPLACE = No   # Replace Existing Destination Subfolder
- RECURSIVE = No   # Unzip Nested Zip Files Recursively
- PRESERVE = No   # Preserve Nested Zip Files
- EXT_S =   # Allowable Source Zip File Extension(s)
- EXT_N =   # Allowable Nested Zip File Extension(s)

Input (input)
    -> ParameterFetcher
ParameterFetcher
    ATTR_LIST = __unzipper.zip_path {$(ZIP_PATH)} __unzipper.root_folder {$(ROOT_FOLDER)} __unzipper.replace {$(REPLACE)} __unzipper.recursive {$(RECURSIVE)} __unzipper.preserve {$(PRESERVE)} __unzipper.ext_s {$(EXT_S)} __unzipper.ext_n {$(EXT_N)}
    -> PythonCaller
PythonCaller
    HIDE_ATTRIBUTES = __unzipper.ext_n __unzipper.zip_path __unzipper.ext_s __unzipper.replace __unzipper.recursive __unzipper.root_folder __unzipper.preserve
    NEW_ATTRIBUTES = path_unix path_windows path_depth __unzipper.flag _error_message
    PYTHONSOURCE:
      # 2016-01-21, Takashi Iijima, Original Implementation
      # 2016-01-23, Takashi Iijima, Updated:
      # - added function to check file extension to prevent extracting non-archiver zip files. e.g. Excel (*.xlsx) etc.
      # - added codes to create desitnation root folder if it is specified but doesn't exist.
      # - added option to preserve nested zip files after unzipping them.
      # - added "path_depth" attribute to output features.
      # 2016-01-25, Takashi Iijima, Updated to trim leading and trailing whitespaces of specified path strings.
      # 2018-06-14, Takashi Iijima, Added Allowable Source/Nested Zip File Extention(s) parameter.
      # 2019-01-13, Takashi Iijima, Fixed the destination folder name derived from zip filename which has non-4-letters suffix (e.g. ".xlsx").
      # 2020-01-13, Takashi Iijima, Changed Default Python Interpreter to 3.6+, saved with FME 2017.1.2.1

      import fmeobjects, zipfile, os
      from zipfile import ZipFile

      class ZipExtractor(object):
          def __init__(self):
              self.logger = fmeobjects.FMELogFile()
              self.kFlagFile = 'file'
              self.kFlagDirectory = 'directory'
              self.kFlagReject = 'reject'
              self.kFlagTerminate = 'terminate'
              self.zipExtS = set(['.zip']) # Filename extensions source (root) zip files
              self.zipExtN = set(['.zip']) # Filename extensions for archived (descendant) zip files

          # Returns the number of characters of the zip file extension
          # if the path points a valid zip file, 0 otherwise.
          def zipExtLen(self, path, zipExt):
              _, ext = os.path.splitext(path)
              return len(ext) if (ext.lower() in zipExt and zipfile.is_zipfile(path)) else 0

          def input(self, feature):
              # Retrieve parameter values from feature attributes, then remove the attributes.
              # Zip path may end with a path separator if extracted by the FilenamePartExtractor as "_dirpath".
              zipPath = feature.getAttribute('__unzipper.zip_path').strip().rstrip('\\/')
              rootFolder = feature.getAttribute('__unzipper.root_folder').strip()
              replace = (feature.getAttribute('__unzipper.replace') == 'No') #bylo Yes, ale my nie chcemy nadpisac
              self.recursive = (feature.getAttribute('__unzipper.recursive') == 'Yes')
              self.preserve = (feature.getAttribute('__unzipper.preserve') == 'Yes')
              extS = set(feature.getAttribute('__unzipper.ext_s').split())
              extN = set(feature.getAttribute('__unzipper.ext_n').split())
              feature.removeAttrsWithPrefix('__unzipper.')

              if extS:
                  self.zipExtS = set([(e if e.startswith('.') else ('.%s' % e)).lower() for e in extS])
              if extN:
                  self.zipExtN = set([(e if e.startswith('.') else ('.%s' % e)).lower() for e in extN])

              # If destination root folder is specified but doesn't exist, try creating the directory.
              isRootValid = True
              if rootFolder and not os.path.exists(rootFolder):
                  try:
                      os.makedirs(rootFolder)
                  except:
                      isRootValid = False

              # If specified zip file or destination root folder is invalid, reject the input feature.
              if not os.path.exists(zipPath) \
                  or self.zipExtLen(zipPath, self.zipExtS) == 0 \
                  or not isRootValid:
                  msg = 'Specified zip file or destination root folder is invalid.'
                  self.logger.logMessageString(msg, fmeobjects.FME_ERROR)
                  feature.setAttribute('_error_message', msg)
                  feature.setAttribute('__unzipper.flag', self.kFlagReject)
                  self.pyoutput(feature)
                  return

              # Define destination folder path: <root folder>/<source zip file name without extension>
              # If root folder is not specified, treat the folder containing source zip file as root folder.
              zipPath = os.path.abspath(zipPath)
              zipFolder, zipName = os.path.split(zipPath)
              rootName, _ = os.path.splitext(zipName)
              destFolder = os.path.join(os.path.abspath(rootFolder) if rootFolder else zipFolder, rootName)

              try:
                  # If the destination folder exists,
                  # - remove the existing folder and all files within it when REPLACE is set to Yes,
                  # - add suffix to the folder path when REPLACE is set to No.
                  if os.path.exists(destFolder):
                      if replace:
                          for dirpath, dirs, files in os.walk(destFolder, topdown=False):
                              for name in files:
                                  os.remove(os.path.join(dirpath, name))
                              for name in dirs:
                                  os.rmdir(os.path.join(dirpath, name))
                          os.rmdir(destFolder)
                      else:
                          format, n = '%s_%d', 1
                          while os.path.exists(format % (destFolder, n)): n += 1
                          destFolder = format % (destFolder, n)
                          #destFolder = destFolder

                  # Extract the zip file and output features containing extracted file/directory path.
                  self.pathInfos = [] # tuples list - (file or directory path, flag: 'file' or 'directory', depth)
                  self.extract(zipPath, destFolder, 1)
                  #ZipFile.extractall(destFolder, None, None)
                  for path, flag, depth in self.pathInfos:
                      feat = feature.cloneAttributes()
                      feat.setAttribute('path_unix', path.replace('\\', '/'))
                      feat.setAttribute('path_windows', path.replace('/', '\\'))
                      feat.setAttribute('path_depth', depth)
                      feat.setAttribute('__unzipper.flag', flag)
                      self.pyoutput(feat)

              except Exception as ex:
                  msg = 'Unexpected error: %s' % ex
                  self.logger.logMessageString(msg, fmeobjects.FME_ERROR)
                  feature.setAttribute('_error_message', msg)
                  feature.setAttribute('__unzipper.flag', self.kFlagTerminate)
                  self.pyoutput(feature)

          # Extract a zip file.
          def extract(self, zipPath, destPath, depth):
              #with zipfile.ZipFile(zipPath) as z: z.extractall(destPath)
              #self.findFiles(destPath, depth)
              with zipfile.ZipFile(zipPath) as zip:
                  for zip_info in zip.infolist():
                      if zip_info.filename[-1] == '/':
                          continue
                      zip_info.filename = os.path.basename(zip_info.filename)
                      zip.extract(zip_info, destPath)

          # Find and collect extracted file/directory paths.
          def findFiles(self, dirPath, depth):
              self.pathInfos.append((dirPath, self.kFlagDirectory, depth))
              depth += 1
              for fname in os.listdir(dirPath):
                  path = os.path.join(dirPath, fname)
                  if os.path.isdir(path):
                      self.findFiles(path, depth)
                  elif self.recursive:
                      n = self.zipExtLen(path, self.zipExtN)
                      if n != 0:
                          if self.preserve:
                              self.pathInfos.append((path, self.kFlagFile, depth))
                              self.extract(path, os.path.join(dirPath, fname[:-n]), depth)
                          else:
                              self.extract(path, os.path.join(dirPath, fname[:-n]), depth)
                              os.remove(path)
                      else:
                          self.pathInfos.append((path, self.kFlagFile, depth))
                  else:
                      self.pathInfos.append((path, self.kFlagFile, depth))
    PYTHONSYMBOL = ZipExtractor
    -> AttributeFilter
AttributeFilter
    ATTR_NAME = __unzipper.flag
    ATTR_VALUES = file,directory,reject,terminate,<EMPTY>,<MISSING>,<NULL>,<UNFILTERED>
    file -> File (output)
    directory -> Directory (output)
    reject -> <Rejected> (output)
    terminate -> <Rejected> (output)
File (output)
Directory (output)
<Rejected> (output)

FME custom transformer GzipDecompressor
Decompresses a single gzip file. 
    This transformer assumes the source gzip path ends with '.gz'.
    By default, the destination filename will be the same as the gzip filename excluding '.gz'. For example, if the source gzip filename is 'sample.txt.gz', the destination filename will be 'sample.txt'. Optionally you can also specify the destination filename with the "Destination Filename" parameter. 
    If an error occurred while processing, the input feature will be output via the 
    <Rejected>
     port. 
    This transformer contains a Python script, which was tested with both Python 2.7 and Python 3.4 interpreter.
Parameters
    Source Gzip File Path
    :
    Specify a gzip file path that should be decompressed. The path should end with '.gz'.
    Destination Folder Path
    :
    Specify a folder path to which the destination file should be saved. If you leave blank this parameter, the destination file will be saved into the same name subfolder as the source gzip filename excluding extensions created under the same folder in which the gzip file is saved. 
    Destination Filename
    :
    Optionally you can specify the destination filename.
    Destination File Path Attribute
    :
    Specify an attribute name that stores the destination file path string.

Parameters:
- SRC_PATH =   # Source Gzip File Path
- DEST_FOLDER =   # Destination Folder Path
- DEST_FILENAME =   # Destination Filename
- DEST_PATH_ATTR = _dest_path   # Destination File Path Attribute

Input (input)
    -> ParameterFetcher
ParameterFetcher
    ATTR_LIST = __gzip.src_path {$(SRC_PATH)} __gzip.dest_filename {$(DEST_FILENAME)} __gzip.dest_folder {$(DEST_FOLDER)}
    -> PythonCaller
PythonCaller
    NEW_ATTRIBUTES = __gzip.dest_path __gzip.error
    PYTHONSOURCE:
      # 2016-06-13, Takashi Iijima, Original Implementation
      # This script was tested with both Python 2.7 and Python 3.4 interpreter.

      import fme, fmeobjects
      import os, gzip, shutil
      def gzipDecompress(feature):
          try:
              srcPath = feature.getAttribute('__gzip.src_path')
              if not os.path.exists(srcPath):
                  raise Exception('specified gz file does not exist')
              elif not os.path.isfile(srcPath) or os.path.islink(srcPath):
                  raise Exception('specified gz file path does not point a file')
              elif not srcPath.lower().endswith('.gz'):
                  raise Exception('specified gz file path does not end with \'.gz\'')
              srcPath = os.path.abspath(srcPath)

              dir = feature.getAttribute('__gzip.dest_folder')
              head, tail = os.path.split(srcPath)
              if not dir:
                  dir = os.path.join(head, tail.split('.')[0])
              if not os.path.exists(dir):
                  os.makedirs(dir)
              elif not os.path.isdir(dir) or os.path.islink(dir):
                  raise Exception('specified folder path does not point a directory')
              fname = feature.getAttribute('__gzip.dest_filename')
              fname = fname if fname else '.'.join(tail.split('.')[:-1])
              destPath = os.path.join(os.path.abspath(dir), fname)

              with gzip.open(srcPath, 'rb') as fin, open(destPath, 'wb') as fout:
                  shutil.copyfileobj(fin, fout)
              feature.setAttribute('__gzip.dest_path', destPath)
          except Exception as ex:
              feature.setAttribute('__gzip.error', '%s' % ex)
    PYTHONSYMBOL = gzipDecompress
    -> Tester
Tester
    BOOL_OP = OR
    TEST_CLAUSE = TEST @Value(__gzip.error) = ""
    TEST_MODE = Automatic
    PASSED -> BulkAttributeRenamer
    FAILED -> AttributeRenamer
BulkAttributeRenamer
    ATTRCHOICE = Selected Attributes
    ATTRLIST = __gzip.dest_path
    MODE_CHOICE = RENAME
    PATTERN_ACTION_DISP = PCREGEXPREPLACE
    REPLACE_PATTERN = .+
    REPLACE_STR = $(DEST_PATH_ATTR)
    -> AttributeRemover
AttributeRemover
    REMOVE_ATTRS = __gzip.dest_filename,__gzip.dest_folder,__gzip.src_path,__gzip.error
    -> Output (output)
Output (output)
AttributeRenamer
    ATTR_TABLE = RENAME_SET_DEFAULT __gzip.error > _rejected_reason
    -> AttributeRemover_2
AttributeRemover_2
    REMOVE_ATTRS = __gzip.dest_filename,__gzip.dest_folder,__gzip.dest_path,__gzip.src_path
    -> <Rejected> (output)
<Rejected> (output)

FME custom transformer Landsat8_downloader
Download data about satellite imaginery from USGS, EE

FME custom transformer SentinelAttributeExtractor
Extracts dataset, band and resolution from fme_dataset attribute.

Parameters:
- FME_BASENAME = @Value(fme_basename)   # Fme Basename
- FME_DATASET = @Value(fme_dataset)   # Fme Dataset

Input (input)
    -> GetDatasetPath
GetDatasetPath: SubstringExtractor
    END = -13
    RESULT_ATTR = _dataset_path
    SRC_STRING = @Value(fme_dataset)
    START = 0
    -> GetDataset
GetDataset: SubstringExtractor
    END = -9
    RESULT_ATTR = _dataset
    SRC_STRING = @Value(fme_basename)
    START = 0
    -> BandExtractor
BandExtractor: SubstringExtractor
    END = -9
    RESULT_ATTR = _band
    SRC_STRING = @Value(fme_dataset)
    START = -11
    -> ResolutionExtractor
ResolutionExtractor: SubstringExtractor
    END = -5
    RESULT_ATTR = _resolution
    SRC_STRING = @Value(fme_dataset)
    START = -7
    -> Output (output)
Output (output)

FME custom transformer ZipExtractorAnyExtension
Extracts files archived in a zip file, and then outputs features for every extracted file and directory.
    Each resulting feature has two attributes storing full path string of an extracted file/directory - 
    "path_unix"
    (UNIX style) and 
    "path_windows"
    (Windows style), and also has an attribute that indicates the depth of the file/directory in the extracted directory hierarchy - 
    "path_depth" 
    (integer starting from 1).
    The features containing file path will be output through the File port, and the features containing directory path will be output through the Directory port. 
    All the extracted files will be saved into a subfolder under the folder specified with the "Destination Root Folder" parameter. The subfolder name will be the same as the source zip file name without extension. For example, if the source zip file name is 
    "data.zip"
    and the specified root folder path is 
    "C:\root"
    , extracted files will be saved into 
    "C:\root\data"
    .
    If the same name folder exists under the specified root folder, a number will be added to the destination subfolder name as suffix to differentiate from the existing folder, by default. e.g. 
    "C:\root\data_1"
    , 
    "C:\root\data_2"
    , and so on. 
    If you set "Yes" to the "Replace Existing Destination Subfolder" parameter, the existing subfolder and all files within it will be removed, and then the destination subfolder will be created newly.
    By default, this transformer will NOT unzip zip files that are archived (nested) in the source zip file. If you set "Yes" to the "Unzip Nested Zip Files Recursively" parameter, this transformer unzips all the nested zip files recursively.
    All attributes of the input feature will be propagated to the output features, but the geometry and coordinate system will not be preserved.
    If the specified source zip file or destination root folder is invalid, the input feature will be output through the <Rejected> port.
    Note: The Unzipper (FME Store/Infrastructure) can also be used to unzip a zip file. The ZipExtractor may be useful if you need to specify the destination root folder and/or to unzip nested zip file(s).
Parameters
    Source Zip File
    :
    Specify a zip file that should be extracted. The zip file name can have any extension and not just ".zip".
    Destination Root Folder
    :
    Specify a folder in which a subfolder containing all extracted files should be created. If you leave this parameter blank, this transformer treats the folder containing the source zip file as the destination root folder.
    All the extracted files will be saved into a subfolder under the root folder. The subfolder name will be the same as the source zip file name without extension. For example, if the source zip file name is 
    "data.zip"
    and the specified root folder path is 
    "C:\root"
    , extracted files will be saved into 
    "C:\root\data"
    .
    Replace Existing Destination Subfolder
    :
    By default, a number will be added to the destination subfolder name as suffix if the same name folder exists under the spcified root folder. e.g. 
    "C:\root\data_1"
    , 
    "C:\root\data_2"
    , and so on. If you set "Yes" to this parameter, the existing subfolder and all files within it will be removed, and then the destination subfolder will be created newly. 
    Unzip Nested Zip Files Recursively
    :
    By default, this transformer will NOT unzip zip files that are archived (nested) in the source zip file. If you set "Yes" to this parameter, this transformer unzips all the nested zip files recursively.
    Preserve Nested Zip Files
    :
    By default, zip files nested in the source zip file will be removed after unzipping them, when the "Unzip Nested Zip Files Recursively" parameter is set to "Yes". If you set "Yes" to this parameter, the nested zip files will also be preserved.
    This parameter affects the result only when the "Unzip Nested Zip Files Recursively" parameter is set to "Yes". When the "Unzip Nested Zip Files Recursively" is set to "No", nested zip files always will be preserved regardless of this parameter.

Parameters:
- ZIP_PATH =   # Source Zip File (*..zip)
- ROOT_FOLDER =   # Destination Root Folder
- REPLACE = No   # Replace Existing Destination Subfolder
- RECURSIVE = No   # Unzip Nested Zip Files Recursively
- PRESERVE = No   # Preserve Nested Zip Files

Input (input)
    -> ParameterFetcher
ParameterFetcher
    ATTR_LIST = __unzipper.zip_path {$(ZIP_PATH)} __unzipper.root_folder {$(ROOT_FOLDER)} __unzipper.replace {$(REPLACE)} __unzipper.recursive {$(RECURSIVE)} __unzipper.preserve {$(PRESERVE)}
    -> PythonCaller
PythonCaller
    HIDE_ATTRIBUTES = __unzipper.preserve __unzipper.recursive __unzipper.replace __unzipper.root_folder __unzipper.zip_path
    NEW_ATTRIBUTES = path_unix path_windows path_depth __unzipper.flag _error_message
    PYTHONSOURCE:
      import fmeobjects, zipfile, os

      # 2016-01-21,  Takashi Iijima,  Original Implementation
      # 2016-01-23,  Takashi Iijima,  Updated:
      # - added function to check file extension to prevent extracting non-archiver zip files. e.g. Excel (*.xlsx) etc.
      # - added codes to create desitnation root folder if it is specified but doesn't exist.
      # - added option to preserve nested zip files after unzipping them.
      # - added "path_depth" attribute to output features.
      # 2016-01-25,  Takashi Iijima,  Updated to trim leading and trailing whitespaces of specified path strings.

      class ZipExtractor(object):
          def __init__(self):
              self.kFlagFile = 'file'
              self.kFlagDirectory = 'directory'
              self.kFlagReject = 'reject'
              self.kFlagTerminate = 'terminate'
              self.logger = fmeobjects.FMELogFile()
              self.isZipFile = lambda path: path.lower().endswith('.zip') and zipfile.is_zipfile(path)

          def input(self, feature):
              # Retrieve parameter values from feature attributes, then remove the attributes.
              # Zip path may end with a path separator if extracted by the FilenamePartExtractor as "_dirpath".
              zipPath = feature.getAttribute('__unzipper.zip_path').strip().rstrip('\\/')
              rootFolder = feature.getAttribute('__unzipper.root_folder').strip()
              replace = (feature.getAttribute('__unzipper.replace') == 'Yes')
              self.recursive = (feature.getAttribute('__unzipper.recursive') == 'Yes')
              self.preserve = (feature.getAttribute('__unzipper.preserve') == 'Yes')
              for attr in ['__unzipper.%s' % s for s in ['zip_path', 'root_folder', 'replace', 'recursive', 'preserve']]:
                  feature.removeAttribute(attr)

              # If destination root folder is specified but doesn't exist, try creating the directory.
              isRootValid = True
              if rootFolder and not os.path.exists(rootFolder):
                  try:
                      os.makedirs(rootFolder)
                  except:
                      isRootValid = False

              # If specified zip file or destination root folder is invalid, reject the input feature.
              if not os.path.exists(zipPath) or not isRootValid:
                  self.logger.logMessageString('Specified zip file or destination root folder is invalid.',  \
                      fmeobjects.FME_WARN)
                  feature.setAttribute('__unzipper.flag', self.kFlagReject)
                  self.pyoutput(feature)
                  return

              # Define destination folder path: <root folder>/<source zip file name without extension>
              # If root folder is not specified, treat the folder containing source zip file as root folder.
              zipPath = os.path.abspath(zipPath)
              zipFolder, zipName = os.path.split(zipPath)
              destFolder = os.path.join(os.path.abspath(rootFolder) if rootFolder else zipFolder, zipName[:-4])

              try:
                  # If the destination folder exists,
                  # - remove the existing folder and all files within it when REPLACE is set to Yes,
                  # - add suffix to the folder path when REPLACE is set to No.
                  if os.path.exists(destFolder):
                      if replace:
                          for dirpath, dirs, files in os.walk(destFolder, topdown=False):
                              for name in files:
                                  os.remove(os.path.join(dirpath, name))
                              for name in dirs:
                                  os.rmdir(os.path.join(dirpath, name))
                          os.rmdir(destFolder)
                      else:
                          format, n = '%s_%d', 1
                          while os.path.exists(format % (destFolder, n)): n += 1
                          destFolder = format % (destFolder, n)

                  # Extract the zip file and output features containing extracted file/directory path.
                  self.pathInfos = [] # tuples list - (file or directory path, flag: 'file' or 'directory', depth)
                  self.extract(zipPath,  destFolder, 1)
                  for path, flag, depth in self.pathInfos:
                      feat = feature.cloneAttributes()
                      feat.setAttribute('path_unix', path.replace('\\', '/'))
                      feat.setAttribute('path_windows', path.replace('/', '\\'))
                      feat.setAttribute('path_depth', depth)
                      feat.setAttribute('__unzipper.flag', flag)
                      self.pyoutput(feat)
              except Exception as ex:
                  feature.setAttribute('_error_message', 'Unexpected error: %s' % ex)
                  feature.setAttribute('__unzipper.flag', self.kFlagTerminate)
                  self.pyoutput(feature)

          # Extract a zip file.
          def extract(self, zipPath, destPath, depth):
              with zipfile.ZipFile(zipPath) as z: z.extractall(destPath)
              self.findFiles(destPath, depth)

          # Find and collect extracted file/directory paths.
          def findFiles(self, dirPath, depth):
              self.pathInfos.append((dirPath, self.kFlagDirectory, depth))
              depth += 1
              for fname in os.listdir(dirPath):
                  path = os.path.join(dirPath, fname)
                  if os.path.isdir(path):
                      self.findFiles(path, depth)
                  elif self.recursive and self.isZipFile(path):
                      if self.preserve:
                          self.pathInfos.append((path, self.kFlagFile, depth))
                          self.extract(path, os.path.join(dirPath, fname[:-4]), depth)
                      else:
                          self.extract(path, os.path.join(dirPath, fname[:-4]), depth)
                          os.remove(path)
                  else:
                      self.pathInfos.append((path, self.kFlagFile, depth))
    PYTHONSYMBOL = ZipExtractor
    -> AttributeFilter
AttributeFilter
    ATTR_NAME = __unzipper.flag
    ATTR_VALUES = file,directory,reject,terminate,<EMPTY>,<MISSING>,<NULL>,<UNFILTERED>
    file -> File (output)
    directory -> Directory (output)
    reject -> <Rejected> (output)
    terminate -> AttributeRemover
File (output)
Directory (output)
<Rejected> (output)
AttributeRemover
    REMOVE_ATTRS = __unzipper.flag,path_depth,path_unix,path_windows
    -> Terminator
Terminator
    MESSAGE = @Value(_error_message)
